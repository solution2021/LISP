(defun c:twa( / objs len i obj ent p1 ear_obj pline_vertexs p_len x_sum y_sum nCount x_point y_point x_cen y_cen cen tb ll ur mid dis TAA)
	(vl-load-com)
	(setvar "cmdecho" 0)
	(command "undo" "be")
	(princ "\n정렬할 문자를 선택하세요. : ")
	(setq objs (ssget '((0 . "*TEXT"))))
	(setq len (sslength objs))
	(setq i 0)
  (setq TAA (getstring "정렬 선택 [왼쪽(L))/중심(C)/중간(M)/오른쪽(R)/TL/TC/TR/ML/MC/MR/BL/BC/BR] <Default=왼쪽(L)> : "))
	
	(repeat len
		(setq obj (ssname objs i))
		(setq ent (entget obj))
		(setq p1 (cdr (assoc 10 ent)))
		(command "-boundary" p1 "")
		(setq ear_obj (entlast))
		(setq pline_vertexs (vlax-get (vlax-ename->vla-object ear_obj) 'coordinates))
		(setq p_len 4) ;(/ (length pline_vertexs) 2))
		(setq x_sum 0)
		(setq y_sum 0)		
		(setq nCount 0)
		
		(while pline_vertexs
			(if (< nCount 4)
				(progn
					(setq x_point (car pline_vertexs))
					(setq y_point (cadr pline_vertexs))
					(setq x_sum (+ x_sum x_point))
					(setq y_sum (+ y_sum y_point))
					(setq pline_vertexs (cddr pline_vertexs))
					(setq nCount (+ 1 nCount))
				)
				(setq pline_vertexs nil)
			)
		)
		
		(setq x_cen (/ x_sum p_len))
		(setq y_cen (/ y_sum p_len))
		
		(setq cen (list x_cen y_cen))

		(setq tb (textbox ent))
		(setq ll (mapcar '+ (car tb) p1))
		(setq ur (mapcar '+ ll (mapcar '- (cadr tb) (car tb))))
		(setq mid (polar ll (angle ll ur) (/ (distance ll ur) 2.0)))
		(setq dis (mapcar '- cen mid))

		(command "_move" obj "" dis "")	
		(command "erase" ear_obj "")
		(setq ear_obj nil)
		(setq i (+ 1 i))
	)
	(command "TJUST" objs "" TAA "")
	(command "undo" "e")
	(setvar "cmdecho" 1)	
	(princ)
)
