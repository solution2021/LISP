(defun c:12()
  (command "change" (ssget) "" "p" "c" 1 "")
  (prompt "\n[KSY] [010-4843-7498]")
  (princ))
(defun c:23()
  (command "change" (ssget) "" "p" "c" 2 "")
  (prompt "\n[KSY] [010-4843-7498]")
  (princ))
(defun c:34()
  (command "change" (ssget) "" "p" "c" 3 "")
  (prompt "\n[KSY] [010-4843-7498]")
  (princ))
(defun c:45()
  (command "change" (ssget) "" "p" "c" 4 "")
  (prompt "\n[KSY] [010-4843-7498]")
  (princ))
(defun c:56()
  (command "change" (ssget) "" "p" "c" 5 "")
  (prompt "\n[KSY] [010-4843-7498]")
  (princ))
(defun c:67()
  (command "change" (ssget) "" "p" "c" 6 "")
  (prompt "\n[KSY] [010-4843-7498]")
  (princ))
(defun c:78()
  (command "change" (ssget) "" "p" "c" 7 "")
  (prompt "\n[KSY] [010-4843-7498]")
  (princ))
(defun c:89()
  (command "change" (ssget) "" "p" "c" 8 "")
  (prompt "\n[KSY] [010-4843-7498]")
  (princ))
(defun c:90()
  (command "change" (ssget) "" "p" "c" 9 "")
  (prompt "\n[KSY] [010-4843-7498]")
  (princ))

(defun c:30()
  (command "change" (ssget) "" "p" "c" 30 "")
  (prompt "\n[KSY] [010-4843-7498]")
  (princ))


(defun c:`()
  (setvar "cmdecho" 0)
  ;(setvar "clayer" layer_snc)
  (command "layer" "on" "*" "")  ;모든레이어를 on 한다.
  (prompt "\n전체 레이어 ON")
  (setvar "cmdecho" 1)
  (princ))
;;;
;;;
;;;
(defun c:1(/ ss n k en cly oly) ;선택외의 것은 안보이게.
   (setvar "cmdecho" 0)
   (setq layer_snc(getvar "clayer"))
   (setq ss (ssget))
   (setq n (sslength ss))
   (setq k 0)
   (setq cly (cdr (assoc 8 (entget (ssname ss (1- n))))))
   (command "layer" "s" cly "")
   (command "layer" "off" "*" "" "")
   (while (<= 1 n)
       (setq en (ssname ss k))
       (setq oly (cdr (assoc 8 (entget en))))
       (command "layer" "on" oly "")
       (setq n (- n 1))
       (setq k (+ k 1))
    )
  (setvar "cmdecho" 1)
    (princ)
)

(defun c:``()
  (setvar "cmdecho" 0)
  (command "LayerP")
  (setvar "cmdecho" 1)
  (princ))



(defun c:2(/ ssg layer_snc n k ssg1 ent ass)
  (setvar "cmdecho" 0)
  (setq ssg(ssget))
  (setq layer_snc(getvar "clayer"))
  (setq n (sslength ssg))
  (setq k 0)
  (while (<= 1 n)
    (setq ssg1(ssname ssg k))
    (setq ent(entget ssg1))
    (setq ass(cdr (assoc 8 ent)))
    (if (= layer_snc ass)
      (command "layer" "off" ass "y" "")
      (command "layer" "off" ass ""))
    (setq n (- n 1))
    (setq k (+ k 1))

    )
  (setvar "cmdecho" 1)
  (princ)

  ) 



(defun c:22() ;;선택한거만 안보이게
  (setvar "cmdecho" 0)
  (while T
  (setq layer_snc(getvar "clayer"))
  (setq aa(entget (car (entsel))))
  (setq f (cdr (assoc 8 aa)))
  (if (= layer_snc f)
    (command "layer" "off" f "y" "")
    (command "layer" "off" f ""))
    )
  (setvar "cmdecho" 1)
  (princ)
  )

(defun c:33(/ ent ass)
    ; (setvar "cmdecho" 0)
    ; (setq ss (ssget))
    ; (setq  (sslength ss))
     (setq ent(entget (car (entsel "\nLayer,Color,Linetype Change :"))))
     (setq snc_lay(cdr (assoc 8 ent)))
     (setq snc_ltscale(cdr (assoc 48 ent)))
     (setq snc_col(cdr (assoc 62 ent)))
     (setq snc_linety(cdr (assoc 6 ent)))

  (if (= nil (cdr (assoc 48 ent)))
    (setq sc_line (fix 1)) (setq sc_line(cdr (assoc 48 ent))))
  
     (if (= snc_col nil) (setq snc_col "bylayer"))
     (if (= snc_linety nil) (setq snc_linety "bylayer"))
     (command "layer" "m" snc_lay "")
     (command "color" snc_col)
     (command "linetype" "s" snc_linety "")
    ; (setvar "cmdecho" 1)
     (princ))

(defun c:3()
  (command "laycur")
  )


(defun c:77()
  (setq ss (ssget))
  (command "layer" "lo" "*" "")
(if (/= ss nil)(progn
     (setq n (sslength ss))
     (setq k 0 tn n)
     (setq cly (cdr (assoc 8 (entget (ssname ss (1- n))))))
     (while (<= 1 n)
       (setq en (ssname ss k))
       (setq oly (cdr (assoc 8 (entget en))))
       (command "layer" "u" oly "")
       (setq n (- n 1))
       (setq k (+ k 1))
     )
     )
  )
  )

(defun c:88()
  (setq ss (ssget))
  (command "layer" "u" "*" "")
(if (/= ss nil)(progn
     (setq n (sslength ss))
     (setq k 0 tn n)
     (setq cly (cdr (assoc 8 (entget (ssname ss (1- n))))))
     (while (<= 1 n)
       (setq en (ssname ss k))
       (setq oly (cdr (assoc 8 (entget en))))
       (command "layer" "lo" oly "")
       (setq n (- n 1))
       (setq k (+ k 1))
     ))))

(defun c:7(/ ss n k en cly oly)
   (prompt "\nCommand: Select Unlock...")
   (prompt "\nUnlock 레이어만을 선택<*.*>-> ")
   (setq ss (ssget))
   (if (= ss nil) (progn
       (command "layer" "lo" "*" "")
       (prompt "\nAll layer is unlock")
   ))
   (if (/= ss nil)(progn
     (setq n (sslength ss))
     (setq k 0 tn n)
     (setq cly (cdr (assoc 8 (entget (ssname ss (1- n))))))
     (while (<= 1 n)
       (setq en (ssname ss k))
       (setq oly (cdr (assoc 8 (entget en))))
       (command "layer" "lo" oly "")
       (setq n (- n 1))
       (setq k (+ k 1))
     )
    ))
    (princ)
)


(defun c:8(/ ss n k en cly oly)
   (prompt "\nCommand: Select Unlock...")
   (prompt "\nUnlock 레이어만을 선택<*.*>-> ")
   (setq ss (ssget))
   (if (= ss nil) (progn
       (command "layer" "u" "*" "")
       (prompt "\nAll layer is unlock")
   ))
   (if (/= ss nil)(progn
     (setq n (sslength ss))
     (setq k 0 tn n)
     (setq cly (cdr (assoc 8 (entget (ssname ss (1- n))))))
     (while (<= 1 n)
       (setq en (ssname ss k))
       (setq oly (cdr (assoc 8 (entget en))))
       (command "layer" "u" oly "")
       (setq n (- n 1))
       (setq k (+ k 1))
     )
    ))
    (princ)
)



;;=====================================================
;  색상바꾸기(2002.03 주말농부)
;  ->현재레이어 또는 선택객체의 색상을 바꾸는 명령어
;  ->선택객체바꾸기 추가(2008.1.6)
;;------ color change ---------------------------------
(defun c:cv(/ cl ss ocn ncn)
   (setq cl (getvar "clayer"))
   (prompt "\n객체선택 [현재 레이어 색상변경]")
   (setq ss (ssget))
   (if ss
      (progn
         (setq ocn 256)
         (setq ncn (acad_colordlg ocn))
         (if (= ncn 256) (setq ncn "bylayer"))
         (if (= ncn 0) (setq ncn "byblock"))
         (vl-cmdf "change" ss "" "p" "c" ncn "")
      )
      (progn
         (setq entl (tblsearch "layer" cl))
         (setq ocn (cdr (assoc 62 entl)))
         (setq ncn (acad_colordlg ocn nil))
         (vl-cmdf "layer" "c" ncn cl "")
      )
   )
(prin1))
