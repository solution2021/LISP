(defun c:EEE()
        (setq p1 (getpoint "\n\t First Point :"))
        (setq p2 (getcorner p1 "\t Other Point :"))
        (while  (SETQ A (SSGET "C" p1 p2 (list (cons 0 "INSERT,DIMENSION"))))
                (setq n (sslength a))
                (setq i 0)
                (repeat n
                        (setq x (ssname a i))
                        (command "explode" x)
                        (setq i (1+ i))
                )
         )
        (command "_chprop" "c" p1 p2 "" "la" "0" "c" "bylayer" "lt" "bylayer" "")
        (command "_copyclip" "p" "")
)
