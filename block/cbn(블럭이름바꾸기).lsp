;***********블럭이름변경**********************
(defun c:cbn (/ ss1 blk_n blk_name)
   (setq k_cnt_1 0)
   (prompt "\n 블럭선택 :")
   (while (<= k_cnt_1 100)
          (setq ss1 (car (entsel)))
          (if (= ss1 nil) (prompt " 블럭만찍어욧!")
              (progn (setq ss1_0 (cdr (assoc 0 (entget ss1)))) 
                     (if (= ss1_0 "INSERT") (setq k_cnt_1 1000)
                         (prompt "\t 다시 블럭선택 : ")
                     )
              )
          )
   )
   (setq blk_n (cdr (assoc 2 (entget ss1))))
   (setq k_cnt_2 0)
   (prin1 blk_n)
   (while (<= k_cnt_2 100)
          (setq blk_name (getstring "\n 블럭명 입력 :"))
          (setq blk_jung (assoc 2 (tblsearch "block" blk_name)))
          (if (= blk_name "") (prompt " 이름안쓰면혼나요~")
                              (if (= blk_jung nil) (setq k_cnt_2 1000)
                                                   (prompt " 이름이겹쳐요!!")
                              )
          )
   )
   (command "rename" "b" blk_n blk_name)
   (princ)
)
