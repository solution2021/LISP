(defun c:mh(/ originalpattern targethatches ss1 ss2 ss3 ss4 n mark)
	(setvar "cmdecho" 0)
	(vla-StartUndoMark (vla-get-ActiveDocument (vlax-get-acad-object)))
;	(command "._undo" "_begin")
	(setq originalpattern (car (entsel "\n패턴으로 사용할 해치를 선택하세요")))
	(if (= originalpattern nil)
		(setq originalpattern (car (entsel "\n패턴으로 사용할 해치를 다시 선택하세요")))
	)
	(princ "\n하나로 합칠 해치들을 선택하세요")
	(setq targethatches (ssget '((0 . "hatch"))))
	(setq n 0)
	(setq ss1 (ssadd))
	(repeat (sslength targethatches)
		(setq ss1 (ssadd (ssname targethatches n) ss1))
		(setq n (1+ n))
	);타겟으로 선택된 해치들의 객체 이름을 ss1에 저장
	(setq mark (entlast))
	(command "hatchgenerateboundary" ss1 "")
	(setq ss2 (ssadd))
	(while 
		(setq mark (entnext mark))
		(setq ss2 (ssadd mark ss2))
	)
	(setq mark (entlast))
	(command "region" ss2 "")
	(setq ss3 (ssadd))
	(while 	
		(setq mark (entnext mark))
		(setq ss3 (ssadd mark ss3))
	)
	(command "union" ss3 "")
	(setq ss4 (entlast))
	(command "._hatch" "s" ss4 "")
	(entdel ss4)
	(command "._matchprop" originalpattern (entlast) "")
	(setq n 0)
	(repeat (sslength targethatches)
		(entdel (ssname ss1 n))
		(setq n (1+ n))
	)
	(vla-endundomark (vla-get-ActiveDocument (vlax-get-acad-object)))
;	(command "._undo" "_end")
)
