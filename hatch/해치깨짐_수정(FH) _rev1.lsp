(defun c:FH( / objs n i obj ent org_p)
	(setvar "cmdecho" 0)
	(princ "\n문제가 되는 해치를 선택해주세요. ")
	(command "undo" "be" "")
	(setq objs (ssget '((0 . "HATCH"))))
	(setq n (sslength objs))
	(setq i 0)
	(repeat n
		(setq obj (ssname objs i))
		(setq ent (entget obj))
		(setq org_p (cadr (mapcar 'cdr (vl-remove-if-not '(lambda (x) (= (car x) 10)) ent))))
		(command "-hatchedit" obj "" "o" "s" org_p "")
		(setq i (+ 1 i))
	)
	(command "undo" "end" "")	
	(setvar "cmdecho" 1)	
	(princ)
)
