(DEFUN C:ds(/ eg egl n l ne entname entn p1 p2 l2 radi l_ength)
      (SETVAR "cmdecho" 0)
	(SETQ EG (SSGET))
	(SETQ EGL (SSLENGTH EG))
	(SETQ N 0)
	(setq l 0)
	(setq ne 0)
	(WHILE (< N EGL)
		(SETQ ENTN (SSNAME EG N))
		(SETQ ENT (ENTGET ENTN))
		(setq entname (assoc 0 ent))
		(setq entname (cdr entname))
		(if (= entname "LINE")
			(progn
				(SETQ p1 (ASSOC 10 ENT))
				(SETQ p2 (ASSOC 11 ENT))
				(SETQ p1x (car (CDR p1)))
				(SETQ p1y (CaDdR p1))
				(SETQ p2x (car (CDR p2)))
				(SETQ p2y (CaDdR p2))
				(setq l2 (sqrt (+ (expt (- p1x p2x) 2) (expt (- p1y p2y) 2))))	
				(setq l (+ l l2))
				(setq  ne (+ ne 1))
			)
		)
		(if (= entname "CIRCLE")
			(progn
				(SETQ p1 (ASSOC 40 ENT))
				(SETQ radi (cdr p1))
				(setq l2 (* 2 (* pi radi)))
				(setq l (+ l l2))
				(setq  ne (+ ne 1))
			)
		)
		(if (= entname "ARC")
			(progn
				(SETQ p1 (ASSOC 40 ENT))
				(SETQ radi (cdr p1))
				(SETQ p1 (ASSOC 50 ENT))
				(SETQ p2 (ASSOC 51 ENT))
				(SETQ p1R (CDR p1))
				(SETQ p2R (CDR p2))
				(SETQ TH (ABS (- P1R P2R)))
				(setq l2 (* RADI TH))
				(setq l (+ l l2))
				(setq  ne (+ ne 1))
			)
		)
            (if (or (= entname "LWPOLYLINE")(= entname "POLYLINE"))
                  (progn
     		            (command "area" "e" entn)
            	      (setq l2 (getvar "perimeter"))
				(setq l (+ l l2))
				(setq  ne (+ ne 1))
	            )
            ) 
		(SETQ N (+ 1 N))
	)
	(princ "\n >>>>> ")
	(if (> egl ne)
		(progn
			(princ ne)(princ " of ")(princ egl)
			(princ " objects are measured // ")
		)
	)
	(princ " Total length is  ")
	(setq l_ength (rtos (/ l 1000) 2 2))
	(prin1 l_ength)
        (setq pt (getpoint "\nText Point: "))
               (setq h (getvar "textsize"))
               (prompt "\nText Height: ")
               (princ H)
               (princ "  : ")
               (setq z (getdist))
               (if z
                   (setq h z)
               )
               (command "text"
                        (setq z pt)
                        (setq z h)
                        (setq z 0.0)
                        (setq z l_ength)
               )
	(setvar "cmdecho" 1)
	(setvar "blipmode" 1)
	(princ)
)
