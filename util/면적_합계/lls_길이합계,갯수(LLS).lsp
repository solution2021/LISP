(defun c:lls (/ ent n dis ent_l #a #ad #as )
(setvar "cmdecho" 0)
(setq ent (ssget '((0 . "LINE,CIRCLE,ARC,POLYLINE,LWPOLYLINE,ELLIPSE,SPLINE"))))
(setq n 0 dis 0)
(repeat (sslength ent)
(setq ent_l (ssname ent n))
(command "lengthen" ent_l "" "" "")
(setq dis (+ dis (GETVAR "PERIMETER")))
(setq n (1+ n))
)
(setq dis (/ dis 1000))
(setq #a (strcat "선택 객체수 = "(rtos n)"     길이합계 = " (rtos dis)))
(prompt (strcat "\n" #a))
(vl-load-com)
(setq #ad (vla-get-activedocument (vlax-get-acad-object)))
(setq #as
(if (> (vla-get-activespace #ad) 0)
(vla-get-modelspace #ad)
(vla-get-paperspace #ad)
);;if
);;setq 
(vla-addtext #as #a (vlax-3d-point (getpoint "\nText Point : "))(* (getvar "textsize")1.0))
(mapcar 'vlax-release-object (list #as #ad)) 
(princ)
(setvar "cmdecho" 1)
)
