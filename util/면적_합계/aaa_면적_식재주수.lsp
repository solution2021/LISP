(defun c:aaa ()
(setq a (ssget))
(command "_area" "O" a)(print)
(setq sh (getvar "area"))
(if (= x1 nil) (setq x1 0))
(princ "m2당 몇주? <")(prin1 x1)(setq x2 (getreal "> : "))
(if (= x2 nil) (setq x2 x1))
(setq sum (* (/ sh 1000000) x2))
(princ "식재 주수 = ")(prin1 sum)(princ "주")(print)
(setq x1 x2)(print)
)
