(DEFUN C:AA()
  (SETVAR "CMDECHO" 1)
  (SETVAR "REGENMODE" 0)
  (COMMAND "AREA" "e" pause)
  (setvar "lunits" 2)
  (setvar "luprec" 2)
  (SETQ PP (GETPOINT "\n Pick the point : ")
        TS (GETVAR "TEXTSIZE")
        AREA (GETVAR "AREA")
        AA (/ AREA 1000000.)
        AREA1 (RTOS AA 2 3)
        AREA2 (RTOS (* AA 0.3025) 2 3)
        AA (STRCAT  "" AREA1 "§³ /" AREA2 "PY" "")
        )
  (COMMAND "TEXT" PP TS "0" AA)
)
