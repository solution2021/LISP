(defun c:lle ()
(setvar "cmdecho" 0)
(setq ent (ssget '((0 . "LINE,CIRCLE,ARC,POLYLINE,LWPOLYLINE,ELLIPSE,SPLINE"))))
(setq n 0 dis 0)
(repeat (sslength ent)
(setq ent_l (ssname ent n))
(command "lengthen" ent_l "")
(setq dis (+ dis (GETVAR "PERIMETER")))
(setq n (1+ n))
)
(prompt (strcat "\n***** 선택 객체수 = "(rtos n)" 길이합계 = " (rtos dis)))(princ)
(setvar "cmdecho" 1)
)
