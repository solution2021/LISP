(defun c:JJJ (/ oSel oldpedit oldcmd b2004 sFilter *error*)
   (setq oldpedit (getvar "PEDITACCEPT"))
   (setq oldcmd (getvar "cmdecho"))   
   (setvar "cmdecho" 0)
   (setq b2004 (>= (substr (getvar "ACADVER") 1 2) "16"))
   (if b2004 (setvar "PEDITACCEPT" 1))
   (setq sFilter '((0 . "LINE,ARC,POLYLINE,LWPOLYLINE") (-4 . "<not") (-4 . "<xor") (70 . 1) (70 . 129) (-4 . "xor>") (-4 . "not>")))
   (princ "\n결합할 선, 폴리선, 호 선택: ")
   (setq oSel (ssget ":L" sFilter))
   (if (/= oSel nil)
      (if (> (sslength oSel) 1)
         (progn
            ;(command ".pedit" "m" oSel "" "j" "j" "b" "0.00001" "")
            (command ".pedit" "m" oSel "" "j" "" "")
         )
      )
   )
   (if b2004 (setvar "PEDITACCEPT" oldpedit))
   (setvar "cmdecho" oldcmd)
   
   (defun *error* (msg)(princ "에러: ")(princ msg)
      (setvar "cmdecho" 1)
   (princ))
   (princ)
)
