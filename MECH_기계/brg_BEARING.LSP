;;********** ***************************************************
;;* BALL BEARING/THRUST BRG/LOCK&NUT/UCP BRG/DU BUSH           *
;;* 1999/7/12                                By K.W.Park       *
;;**************************************************************
(defun brg_er (s)
 (if (/= s "Function Cancelled")
 (if (= s "quit / exit abort")
 (princ)
 (princ (strcat "\nERROR :" s))
 )
 )
 (setvar "cmdecho" ocmde)                               
 (setvar "osmode" oosmo)
 (setvar "peditaccept" oed) 
 (setq *error* olderr)
 (princ)
)
;;;;;;;;;;;;;;;;;;;
(defun dtr (dtr1)
 (* pi (/ dtr1 180.0))
)
;--------------------------------------------------------------
(defun c:brg (/ an1 d od b r thk bd br x pt pb p1 p2 p3 oed
   p4 p5 p6 p7 p8 p9 p10 p11 p12 p13 p14 p15 ep1 ep2 ep3 ep4
   ep5 ep6 ep7 ep8 ep9 ep10 f1 f2 f3 f4 k nd  olderr opd x2
   size ep11 ep12 ep13 ep14 ep15 ep16 ep17 ep18 an1 o1 thk
   o2 d1 t1 w1 dr1 w2 dr2 bd p16 p17 p18 p19 p20 p21  ocmde 
   f5 f6 f7 f8 pt p22 p23 nd olderr size f10 f11 f12 oosmo
   f13 f14 f15 f16 f17 an1 d1 nd d3 d4 g s d6 bn r ph d2 x1 l1 
   p15 ans an2 po k e tk d5 z de1 de2 dg1 dg2 dg3 h1 h2 le1 x2
   rl rc tbc tbh an1 do be n m g m1 p l a j h1 h n1 n2 h2 m2
   w gd of dor beh dgo dg1 dg2 h3 l1 wh1 tt bd h4 po p24 tbl
   p25 p26 p27 p28 p29 p30 p31 p32 p33 p34 p35 p36 p37 p38 p39 p40
   p41 p42 p43 p44 p45 p46 e1 e2 e3 e4 e5 e6 e6a e6b e7 e8 e8a e9
   e9a e10 e11 e12 e13 e13a e13b e13c e13d e14 e15 e16 e17 e18 e19
   e20 e21 e22 e23 e24 sh ed14 el et eh ucp o c c1 c2 tb1 tb2)
(command "undo" "be")   
(setq olderr *error* *error* brg_er)
(setq ocmde (getvar "cmdecho"))
(setq oosmo (getvar "osmode"))
(setvar "cmdecho" 0)
(setvar "osmode" 0)
(setq oed (getvar "peditaccept"))
(setvar "peditaccept" 0)  
(setq tbl (tblsearch "layer" "cen-m")) 
    (if (= tbl nil)
     (command "layer" "n" "cen-m" "c" 6 "cen-m" "lt" "center2" "cen-m" "")
    )
(setq tb2 (tblsearch "LAYER" "hid-r")) 
  (if (= tb2 nil)
   (command "layer" "n" "hid-r" "c" 1 "hid-r" "l" "hidden" "hid-r" "")
  )  
;-------------------------------------------------------------------------------------------------------
(setq ans (getint "\nSelect No.<1.Ball bearing  2.Thrust bearing  3.Lock&nut  4.UCP bearing  5.DU bush>: " ))
;-------------------------------------------------------------------------------------------------------
(if (= ans 1)
 (progn 
  (setq an1 (getreal "\nBall Bearing No.? [ex: 683,693,603,6803,6903,6202,6303,16001]: " ))
  (if (= an1 nil) (exit))
(cond
((= an1 683) (setq size '(683 3 7 2 0.3)))
((= an1 693) (setq size '(693 3 8 3 0.3)))
((= an1 603) (setq size '(603 3 9 3 0.3)))
((= an1 684) (setq size '(684 4 9 2.5 0.3)))
((= an1 694) (setq size '(694 4 11 4 0.3)))
((= an1 604) (setq size '(604 4 12 4 0.4)))
((= an1 685) (setq size '(685 5 11 3 0.3)))
((= an1 695) (setq size '(695 5 13 4 0.4)))
((= an1 605) (setq size '(605 5 14 5 0.4)))
((= an1 686) (setq size '(686 6 13 3.5 0.3)))
((= an1 696) (setq size '(696 6 15 5 0.4)))
((= an1 606) (setq size '(606 6 17 6 0.5)))
((= an1 687) (setq size '(687 7 14 3.5 0.3)))
((= an1 697) (setq size '(697 7 17 5 0.5)))
((= an1 607) (setq size '(607 7 19 6 0.5)))
((= an1 688) (setq size '(688 8 16 4 0.4)))
((= an1 698) (setq size '(698 8 19 6 0.5)))
((= an1 608) (setq size '(608 8 22 7 0.5)))
((= an1 689) (setq size '(689 9 17 4 0.4)))
((= an1 699) (setq size '(699 9 20 6 0.5)))
((= an1 609) (setq size '(609 9 24 7 0.5)))
((= an1 6800) (setq size '(6800 10 19 5 0.3)))
((= an1 6900) (setq size '(6900 10 22 6 0.3)))
((= an1 6000) (setq size '(6000 10 26 8 0.5)))
((= an1 6200) (setq size '(6200 10 30 9 0.6)))
((= an1 6300) (setq size '(6300 10 35 11 0.6)))
((= an1 6801) (setq size '(6801 12 21 5 0.3)))
((= an1 6901) (setq size '(6901 12 24 6 0.3)))
((= an1 16001) (setq size '(16001 12 28 7 0.3)))
((= an1 6001) (setq size '(6001 12 28 8 0.3)))
((= an1 6201) (setq size '(6201 12 32 10 0.6)))
((= an1 6301) (setq size '(6301 12 37 12 1.0)))
((= an1 6802) (setq size '(6802 15 24 5 0.3)))
((= an1 6902) (setq size '(6902 15 28 7 0.3)))
((= an1 16002) (setq size '(16002 15 32 8 0.3)))
((= an1 6002) (setq size '(6002 15 32 9 0.3)))
((= an1 6202) (setq size '(6202 15 35 11 0.6)))
((= an1 6302) (setq size '(6302 15 42 13 1.0)))
((= an1 6803) (setq size '(6803 17 26 5 0.3)))
((= an1 6903) (setq size '(6903 17 30 7 0.3)))
((= an1 16003) (setq size '(16003 17 35 8 0.3)))
((= an1 6003) (setq size '(6003 17 35 10 0.3)))
((= an1 6203) (setq size '(6203 17 40 12 0.6)))
((= an1 6303) (setq size '(6303 17 47 14 1.0)))
((= an1 6804) (setq size '(6804 20 32 7 0.3)))
((= an1 6904) (setq size '(6904 20 37 9 0.3)))
((= an1 16004) (setq size '(16004 20 42 8 0.3)))
((= an1 6004) (setq size '(6004 20 42 12 0.6)))
((= an1 6204) (setq size '(6204 20 47 14 1.0)))
((= an1 6304) (setq size '(6304 20 52 15 1.1)))
((= an1 6022) (setq size '(6022 22 44 12 0.6)))
((= an1 6222) (setq size '(6222 22 50 14 1.0)))
((= an1 6322) (setq size '(6322 22 56 16 1.1)))
((= an1 6805) (setq size '(6805 25 37 7 0.3)))
((= an1 6905) (setq size '(6905 25 42 9 0.3)))
((= an1 16005) (setq size '(16005 25 47 8 0.3)))
((= an1 6005) (setq size '(6005 25 47 12 0.6)))
((= an1 6205) (setq size '(6205 25 52 15 1.0)))
((= an1 6305) (setq size '(6305 25 62 17 1.1)))
((= an1 6028) (setq size '(6028 28 52 12 0.6)))
((= an1 6228) (setq size '(6228 28 58 16 1.0)))
((= an1 6328) (setq size '(6328 28 68 18 1.1)))
((= an1 6806) (setq size '(6806 30 42 7 0.3)))
((= an1 6906) (setq size '(6906 30 47 9 0.3)))
((= an1 16006) (setq size '(16006 30 55 9 0.3)))
((= an1 6006) (setq size '(6006 30 55 13 1.0)))
((= an1 6206) (setq size '(6206 30 62 16 1.0)))
((= an1 6306) (setq size '(6306 30 72 19 1.1)))
((= an1 6032) (setq size '(6032 32 58 13 1.0)))
((= an1 6232) (setq size '(6232 32 65 17 1.0)))
((= an1 6332) (setq size '(6332 32 75 20 1.1)))
((= an1 6807) (setq size '(6807 35 47 7 0.3)))
((= an1 6907) (setq size '(6907 35 55 10 0.6)))
((= an1 16007) (setq size '(16007 35 62 9 0.3)))
((= an1 6007) (setq size '(6007 35 62 14 1.0)))
((= an1 6207) (setq size '(6207 35 72 17 1.1)))
((= an1 6307) (setq size '(6307 35 80 21 1.5)))
((= an1 6808) (setq size '(6808 40 52 7 0.3)))
((= an1 6908) (setq size '(6908 40 62 12 0.6)))
((= an1 16008) (setq size '(16008 40 68 9 0.3)))
((= an1 6008) (setq size '(6008 40 68 15 1.0)))
((= an1 6208) (setq size '(6208 40 80 18 1.1)))
((= an1 6308) (setq size '(6308 40 90 23 1.5)))
((= an1 6809) (setq size '(6809 45 58 7 0.3)))
((= an1 6909) (setq size '(6909 45 68 12 0.6)))
((= an1 16009) (setq size '(16009 45 75 10 0.6)))
((= an1 6009) (setq size '(6009 45 75 16 1.0)))
((= an1 6209) (setq size '(6209 45 85 19 1.1)))
((= an1 6309) (setq size '(6309 45 100 25 0.5)))
((= an1 6810) (setq size '(6810 50 65 7 0.3)))
((= an1 6910) (setq size '(6910 50 72 12 0.6)))
((= an1 16010) (setq size '(16010 50 80 10 0.6)))
((= an1 6010) (setq size '(6010 50 80 16 1.0)))
((= an1 6210) (setq size '(6210 50 90 20 1.1)))
((= an1 6310) (setq size '(6310 50 110 27 2.0)))
((= an1 6811) (setq size '(6811 55 72 9 0.3)))
((= an1 6911) (setq size '(6911 55 80 13 1.0)))
((= an1 16011) (setq size '(16011 55 90 11 0.6)))
((= an1 6011) (setq size '(6011 55 90 18 1.1)))
((= an1 6211) (setq size '(6211 55 100 21 1.5)))
((= an1 6311) (setq size '(6311 55 120 29 2.0)))
((= an1 6812) (setq size '(6812 60 78 10 0.3)))
((= an1 6912) (setq size '(6912 60 85 13 1.0)))
((= an1 16012) (setq size '(16012 60 95 11 0.6)))
((= an1 6012) (setq size '(6012 60 95 18 1.1)))
((= an1 6212) (setq size '(6212 60 110 22 1.5)))
((= an1 6312) (setq size '(6312 60 130 31 2.0)))
((= an1 6813) (setq size '(6813 65 85 10 0.6)))
((= an1 6913) (setq size '(6913 65 90 13 1.0)))
((= an1 16013) (setq size '(16013 65 100 11 0.6)))
((= an1 6013) (setq size '(6013 65 100 18 1.1)))
((= an1 6213) (setq size '(6213 65 120 23 1.5)))
((= an1 6313) (setq size '(6313 65 140 33 2.1)))
((= an1 6814) (setq size '(6814 70 90 10 0.6)))
((= an1 6914) (setq size '(6914 70 100 16 1.0)))
((= an1 16014) (setq size '(16014 70 110 13 0.6)))
((= an1 6014) (setq size '(6014 70 110 20 1.1)))
((= an1 6214) (setq size '(6214 70 125 24 1.6)))
((= an1 6314) (setq size '(6314 70 150 35 2.1)))
((= an1 6815) (setq size '(6815 75 95 10 0.6)))
((= an1 6915) (setq size '(6915 75 105 16 1.0)))
((= an1 16015) (setq size '(16015 75 115 13 0.6)))
((= an1 6015) (setq size '(6015 75 115 20 1.1)))
((= an1 6215) (setq size '(6215 75 130 25 1.5)))
((= an1 6315) (setq size '(6315 75 160 37 2.1)))
((= an1 6816) (setq size '(6816 80 100 10 0.6)))
((= an1 6916) (setq size '(6916 80 110 16 1.0)))
((= an1 16016) (setq size '(16016 80 125 14 0.6)))
((= an1 6016) (setq size '(6016 80 125 22 1.1)))
((= an1 6216) (setq size '(6216 80 140 26 2.0)))
((= an1 6316) (setq size '(6316 80 170 39 2.1)))
((= an1 6817) (setq size '(6817 85 110 13 1.0)))
((= an1 6917) (setq size '(6917 85 120 18 1.1)))
((= an1 16017) (setq size '(16017 85 130 14 0.6)))
((= an1 6017) (setq size '(6017 85 130 22 1.1)))
((= an1 6217) (setq size '(6217 85 150 28 2.0)))
((= an1 6317) (setq size '(6317 85 180 41 3.0)))
((= an1 6818) (setq size '(6818 90 115 13 1.0)))
((= an1 6918) (setq size '(6918 90 125 18 1.1)))
((= an1 16018) (setq size '(16018 90 140 16 1.0)))
((= an1 6018) (setq size '(6018 90 140 24 1.5)))
((= an1 6218) (setq size '(6218 90 160 30 2.0)))
((= an1 6318) (setq size '(6318 90 190 43 3.0)))
((= an1 6819) (setq size '(6819 95 120 13 1.0)))
((= an1 6919) (setq size '(6919 95 130 18 1.1)))
((= an1 16019) (setq size '(16019 95 145 16 1.0)))
((= an1 6019) (setq size '(6019 95 145 24 1.5)))
((= an1 6219) (setq size '(6219 95 170 32 2.1)))
((= an1 6319) (setq size '(6319 95 200 45 3.0)))
((= an1 6820) (setq size '(6820 100 125 13 1.0)))
((= an1 6920) (setq size '(6920 100 140 20 1.1)))
((= an1 16020) (setq size '(16020 100 150 16 1.0)))
((= an1 6020) (setq size '(6020 100 150 24 1.5)))
((= an1 6220) (setq size '(6220 100 180 34 2.1)))
((= an1 6320) (setq size '(6320 100 215 47 3.0)))
((= an1 6821) (setq size '(6821 105 130 13 1.0)))
((= an1 6921) (setq size '(6921 105 145 20 1.1)))
((= an1 16021) (setq size '(16021 105 160 18 1.0)))
((= an1 6021) (setq size '(6021 105 160 26 2.0)))
((= an1 6221) (setq size '(6221 105 190 36 2.1)))
((= an1 6321) (setq size '(6321 105 225 49 3.0)))
((= an1 6822) (setq size '(6822 110 140 16 1.0)))
((= an1 6922) (setq size '(6922 110 150 20 1.1)))
((= an1 16022) (setq size '(16022 110 170 19 1.0)))
((= an1 6022) (setq size '(6022 110 170 28 2.0)))
((= an1 6222) (setq size '(6222 110 200 38 2.1)))
((= an1 6322) (setq size '(6322 110 240 50 3.0)))
((= an1 6824) (setq size '(6824 120 150 16 1.0)))
((= an1 6924) (setq size '(6924 120 165 22 1.1)))
((= an1 16024) (setq size '(16024 120 180 19 1.0)))
((= an1 6024) (setq size '(6024 120 180 28 2.0)))
((= an1 6224) (setq size '(6224 120 215 40 2.1)))
((= an1 6324) (setq size '(6324 120 260 55 3.0)))
((= an1 6826) (setq size '(6826 130 165 18 1.1)))
((= an1 6926) (setq size '(6926 130 180 24 1.5)))
((= an1 16026) (setq size '(16026 130 200 22 1.1)))
((= an1 6026) (setq size '(6026 130 200 33 2.0)))
((= an1 6226) (setq size '(6226 130 230 40 3.0)))
((= an1 6326) (setq size '(6326 130 280 58 4.0)))
((= an1 6828) (setq size '(6828 140 175 18 1.1)))
((= an1 6928) (setq size '(6928 140 190 24 1.5)))
((= an1 16028) (setq size '(16028 140 210 22 1.1)))
((= an1 6028) (setq size '(6028 140 210 33 2.0)))
((= an1 6228) (setq size '(6228 140 250 42 3.0)))
((= an1 6328) (setq size '(6328 140 300 62 4.0)))
((= an1 6830) (setq size '(6830 150 190 20 1.1)))
((= an1 6930) (setq size '(6930 150 210 28 2.0)))
((= an1 16030) (setq size '(16030 150 225 24 1.1)))
((= an1 6030) (setq size '(6030 150 225 35 2.1)))
((= an1 6230) (setq size '(6230 150 270 45 3.0)))
((= an1 6330) (setq size '(6330 150 320 65 4.0)))
((= an1 6832) (setq size '(6832 160 200 20 1.1)))
((= an1 6932) (setq size '(6932 160 220 28 2.0)))
((= an1 16032) (setq size '(16032 160 240 25 1.5)))
((= an1 6032) (setq size '(6032 160 240 38 2.1)))
((= an1 6232) (setq size '(6232 160 290 48 3.0)))
((= an1 6332) (setq size '(6332 160 340 68 4.0)))
((= an1 6834) (setq size '(6834 170 215 22 1.1)))
((= an1 6934) (setq size '(6934 170 230 28 2.0)))
((= an1 16034) (setq size '(16034 170 260 28 1.5)))
((= an1 6034) (setq size '(6034 170 260 42 2.1)))
((= an1 6234) (setq size '(6234 170 310 52 4.0)))
((= an1 6334) (setq size '(6334 170 360 72 4.0)))
((= an1 6836) (setq size '(6836 180 225 22 1.1)))
((= an1 6936) (setq size '(6936 180 250 33 2.0)))
((= an1 16036) (setq size '(16036 180 280 31 2.0)))
((= an1 6036) (setq size '(6036 180 280 46 2.1)))
((= an1 6236) (setq size '(6236 180 320 52 4.0)))
((= an1 6336) (setq size '(6336 180 380 75 4.0)))
((= an1 6838) (setq size '(6838 190 240 24 1.5)))
((= an1 6938) (setq size '(6938 190 260 33 2.0)))
((= an1 16038) (setq size '(16038 190 290 31 2.0)))
((= an1 6038) (setq size '(6038 190 290 46 2.1)))
((= an1 6238) (setq size '(6238 190 340 55 4.0)))
((= an1 6338) (setq size '(6338 190 400 78 5.0)))
((= an1 6840) (setq size '(6840 200 250 24 1.5)))
((= an1 6940) (setq size '(6940 200 280 38 2.1)))
((= an1 16040) (setq size '(16040 200 310 34 2.1)))
((= an1 6040) (setq size '(6040 200 310 51 3.0)))
((= an1 6240) (setq size '(6240 200 360 58 4.0)))
((= an1 6340) (setq size '(6340 200 420 80 5.0)))
((= an1 6844) (setq size '(6844 220 270 24 1.5)))
((= an1 6944) (setq size '(6944 220 300 38 2.1)))
((= an1 16044) (setq size '(16044 220 340 37 2.1)))
((= an1 6044) (setq size '(6044 220 340 56 3.0)))
((= an1 6244) (setq size '(6244 220 400 65 4.0)))
((= an1 6344) (setq size '(6344 220 460 88 5.0)))
((= an1 6848) (setq size '(6848 240 300 28 2.0)))
((= an1 6948) (setq size '(6948 240 320 38 2.1)))
((= an1 16048) (setq size '(16048 240 360 37 2.1)))
((= an1 6048) (setq size '(6048 240 360 56 3.0)))
((= an1 6248) (setq size '(6248 240 440 72 4.0)))
((= an1 6348) (setq size '(6348 240 500 95 5.0)))
((= an1 6852) (setq size '(6852 260 320 28 2.0)))
((= an1 6952) (setq size '(6952 260 360 46 2.1)))
((= an1 16052) (setq size '(16052 260 400 44 3.0)))
((= an1 6052) (setq size '(6052 260 400 65 4.0)))
((= an1 6252) (setq size '(6252 260 480 80 5.0)))
((= an1 6352) (setq size '(6352 260 540 102 6.0)))
((= an1 6856) (setq size '(6856 280 350 33 2.0)))
((= an1 6956) (setq size '(6956 280 380 46 2.1)))
((= an1 16056) (setq size '(16056 280 420 44 3.0)))
((= an1 6056) (setq size '(6056 280 420 65 4.0)))
((= an1 6256) (setq size '(6256 280 500 80 5.0)))
((= an1 6356) (setq size '(6356 280 580 108 6.0)))
((= an1 6860) (setq size '(6860 300 380 38 2.1)))
((= an1 6960) (setq size '(6960 300 420 56 3.0)))
((= an1 16060) (setq size '(16060 300 460 50 4.0)))
((= an1 6060) (setq size '(6060 300 460 74 4.0)))
((= an1 6260) (setq size '(6260 300 540 85 5.0)))
((= an1 6864) (setq size '(6864 320 400 38 2.1)))
((= an1 6964) (setq size '(6964 320 440 56 3.0)))
((= an1 16064) (setq size '(16064 320 480 50 4.0)))
((= an1 6064) (setq size '(6064 320 480 74 4.0)))
((= an1 6264) (setq size '(6264 320 580 92 5.0)))
((= an1 6868) (setq size '(6868 340 420 38 2.1)))
((= an1 6968) (setq size '(6968 340 460 56 3.0)))
((= an1 6068) (setq size '(6068 340 520 82 5.0)))
((= an1 6268) (setq size '(6268 340 620 92 6.0)))
((= an1 6872) (setq size '(6872 360 440 38 2.1)))
((= an1 6972) (setq size '(6972 360 480 56 3.0)))
((= an1 6072) (setq size '(6072 360 540 82 5.0)))
((= an1 6272) (setq size '(6272 360 650 95 6.0)))
((= an1 6876) (setq size '(6876 380 480 46 2.1)))
((= an1 6976) (setq size '(6976 380 520 65 4.0)))
((= an1 6076) (setq size '(6076 380 560 82 5.0)))
((= an1 6880) (setq size '(6880 400 500 46 2.1)))
((= an1 6980) (setq size '(6980 400 540 65 4.0)))
((= an1 6080) (setq size '(6080 400 600 90 5.0)))
((= an1 6884) (setq size '(6884 420 520 46 2.1)))
((= an1 6984) (setq size '(6984 420 560 65 4.0)))
((= an1 6084) (setq size '(6084 420 620 90 5.0)))
((= an1 6888) (setq size '(6888 440 540 46 2.1)))
((= an1 6988) (setq size '(6988 440 600 74 4.0)))
((= an1 6088) (setq size '(6088 440 650 94 6.0)))
((= an1 6892) (setq size '(6892 460 580 56 3.0)))
((= an1 6992) (setq size '(6992 460 620 74 4.0)))
((= an1 6092) (setq size '(6092 460 680 100 6.0)))
((= an1 6896) (setq size '(6896 480 600 56 3.0)))
((= an1 6996) (setq size '(6996 480 650 78 5.0)))
((= an1 6096) (setq size '(6096 480 700 100 6.0)))
((= an1 68500) (setq size '(68500 500 620 56 3.0)))
((= an1 69500) (setq size '(69500 500 670 78 5.0)))
((= an1 60500) (setq size '(60500 500 720 100 6.0)))
((= an1 68530) (setq size '(68530 530 650 56 3.0)))
((= an1 69530) (setq size '(69530 530 710 82 5.0)))
((= an1 60530) (setq size '(60530 530 780 112 6.0)))
((= an1 68560) (setq size '(68560 560 680 56 3.0)))
((= an1 69560) (setq size '(69560 560 750 85 5.0)))
((= an1 60560) (setq size '(60560 560 820 115 6.0)))
((= an1 68600) (setq size '(68600 600 730 60 3.0)))
((= an1 69600) (setq size '(69600 600 800 90 5.0)))
((= an1 60600) (setq size '(60600 600 870 118 6.0)))
((= an1 68630) (setq size '(68630 630 780 69 4.0)))
((= an1 69630) (setq size '(69630 630 850 100 6.0)))
((= an1 60630) (setq size '(60630 630 920 128 7.5)))
((= an1 68670) (setq size '(68670 670 820 69 4.0)))
((= an1 69670) (setq size '(69670 670 900 103 6.0)))
((= an1 60670) (setq size '(60670 670 980 136 7.5)))
((= an1 68710) (setq size '(68710 710 870 74 4.0)))
((= an1 69710) (setq size '(69710 710 950 106 6.0)))
((= an1 68750) (setq size '(68750 750 920 78 5.0)))
((= an1 69750) (setq size '(69750 750 1000 112 6.0)))
((= an1 68800) (setq size '(68800 800 980 82 5.0)))
((= an1 69800) (setq size '(69800 800 1060 115 6.0)))
)       ;;;;bearing total:304ea
 (if (= size nil)
  (progn
    (princ "\nNot Exist Bearing No.!")
    (exit)
  )
 )   
(setq nd (nth 0 size)            ;brg no.
       d (nth 1 size)            ;brg id
      od (nth 2 size)            ;brg od
       b (nth 3 size)            ;brg width
       r (nth 4 size)            ;brg corner radius
     thk (/ (- od d) 2.0)        ;(od-d)/2      
       k 2.0)
  (if (or (= an1 16001)(= an1 16002)(= an1 16003)(= an1 16004)(= an1 16005)
          (= an1 16006)(= an1 16007)(= an1 16008)(= an1 16009)(= an1 16010)
          (= an1 16011)(= an1 16012)(= an1 16013)(= an1 16014)(= an1 16015)
          (= an1 16016)(= an1 16017)(= an1 16018)(= an1 16019)(= an1 16020)
          (= an1 16021)(= an1 16022)(= an1 16024)(= an1 16026)(= an1 16028)
          (= an1 16030)(= an1 16032)(= an1 16034)(= an1 16036)(= an1 16038)
          (= an1 16040)(= an1 16044)(= an1 16048)(= an1 16052)(= an1 16056)
          (= an1 16060)(= an1 16064))
   (setq k 1.4)
  );if
(setq bd (* thk (/ k 3.0))         ;ball dia.(about)
      br (/ bd 2.0)                ;ball radius
       x (* br (cos (dtr 30.0))))
(setq pt (getpoint "\ninsert point : " ))
 (if (= pt nil) (exit))
(setq p1 (polar pt (dtr 90) (/ d 2.0))
      p2 (polar p1 (dtr 90) thk)
      p3 (polar p2 (dtr 180) b)
      p4 (polar p3 (dtr 270) thk)
      p5 (polar p4 (dtr 90) (/ thk 2.0))
      p6 (polar p5 (dtr 0) b)
      pb (polar p5 (dtr 0) (/ b 2.0))
      p7 (polar pb (dtr 330) br)
      p8 (polar p7 (dtr 0) (- (/ b 2.0) x))
      p9 (polar pb (dtr 210) br)
     p10 (polar p9 (dtr 180) (- (/ b 2.0) x))
     p11 (polar p1 (dtr 90) r)
     p12 (polar p11 (dtr 180) b)
     p13 (polar p12 (dtr 270) (+ d (* r 2.0)))
     p14 (polar p13 (dtr 0) b)
     p15 (polar pt (dtr 180) b))   ;mirror line 
(command "line" p1 p2 "")  (setq ep1 (entlast))
(command "line" p2 p3 "")  (setq ep2 (entlast))
(command "line" p3 p4 "")  (setq ep3 (entlast))
(command "line" p4 p1 "")  (setq ep4 (entlast))
(command "fillet" "r" r)
(command "fillet" ep1 ep2) (setq f1 (entlast))
(command "fillet" ep2 ep3) (setq f2 (entlast))
(command "fillet" ep3 ep4) (setq f3 (entlast))
(command "fillet" ep4 ep1) (setq f4 (entlast))
(command "pedit" ep1 "" "j" ep1 f1 ep2 f2 ep3 f3 ep4 f4 "" "") (setq ep10 (entlast))  
(command "line" p9 p10 "") (setq ep5 (entlast))
(command "line" p7 p8 "")  (setq ep6 (entlast))
(command "mirror" ep5 "" p5 p6 "") (setq ep7 (entlast))
(command "mirror" ep6 "" p5 p6 "") (setq ep8 (entlast))
(command "circle" pb "d" bd)       (setq ep9 (entlast))
(command "mirror" ep10  "" p15 pt "")  (setq ep11 (entlast))
(command "mirror" ep5  "" p15 pt "")   (setq ep14 (entlast))
(command "mirror" ep6  "" p15 pt "")   (setq ep15 (entlast))
(command "mirror" ep7  "" p15 pt "")   (setq ep16 (entlast))
(command "mirror" ep8  "" p15 pt "")   (setq ep17 (entlast))
(command "mirror" ep9  "" p15 pt "")   (setq ep18 (entlast))
(command "line" p12 p13 "") (setq ep12 (entlast))
(command "line" p11 p14 "") (setq ep13 (entlast))  
(command "rotate" ep10 ep5 ep6 ep7 ep8 ep9 ep11 ep12 ep13 ep14 ep15 ep16 ep17 ep18 "" pt "\\")
(princ (strcat "\nYou select: " (rtos an1) " (" (rtos d) "x" (rtos od)
                              "x" (rtos b) "B) -- Ball Dia is not real size."))  
)
);end if ball brg  
;--------------------------------------------------------------------------------------
(if (= ans 2)
 (progn
  (setq opd (getvar "pdmode")) 
  (setvar "pdmode" 3) 
(initget 7)
(setq an1 (getreal "\nBearing No.? [ex: 51103,51203,51305,51405]: " ))
(cond
((= an1 51100) (setq size '( 51100 10 24 9 0.3 24 11)))
((= an1 51200) (setq size '( 51200 10 26 11 0.6 26 12)))
((= an1 51101) (setq size '( 51101 12 26 9 0.3 26 13)))
((= an1 51201) (setq size '( 51201 12 28 11 0.6 28 14)))
((= an1 51102) (setq size '( 51102 15 28 9 0.3 28 16)))
((= an1 51202) (setq size '( 51202 15 32 12 0.6 32 17)))
((= an1 51103) (setq size '( 51103 17 30 9 0.3 30 18)))
((= an1 51203) (setq size '( 51203 17 35 12 0.6 35 19)))
((= an1 51104) (setq size '( 51104 20 35 10 0.3 35 21)))
((= an1 51204) (setq size '( 51204 20 40 14 0.6 40 22)))
((= an1 51105) (setq size '( 51105 25 42 11 0.6 42 26)))
((= an1 51205) (setq size '( 51205 25 47 15 0.6 47 27)))
((= an1 51305) (setq size '( 51305 25 52 18 1.0 52 27)))
((= an1 51405) (setq size '( 51405 25 60 24 1.0 60 27)))
((= an1 51106) (setq size '( 51106 30 47 11 0.6 47 32)))
((= an1 51206) (setq size '( 51206 30 52 16 0.6 52 32)))
((= an1 51306) (setq size '( 51306 30 60 21 1.0 60 32)))
((= an1 51406) (setq size '( 51406 30 70 28 1.0 70 32)))
((= an1 51107) (setq size '( 51107 35 52 12 0.6 52 37)))
((= an1 51207) (setq size '( 51207 35 62 18 1.0 62 37)))
((= an1 51307) (setq size '( 51307 35 68 24 1.0 68 37)))
((= an1 51407) (setq size '( 51407 35 80 32 1.1 80 37)))
((= an1 51108) (setq size '( 51108 40 60 13 0.6 60 42)))
((= an1 51208) (setq size '( 51208 40 68 19 1.0 68 42)))
((= an1 51308) (setq size '( 51308 40 78 26 1.0 78 42)))
((= an1 51408) (setq size '( 51408 40 90 36 1.1 90 42)))
((= an1 51109) (setq size '( 51109 45 65 14 0.6 65 47)))
((= an1 51209) (setq size '( 51209 45 73 20 1.0 73 47)))
((= an1 51309) (setq size '( 51309 45 85 28 1.0 85 47)))
((= an1 51409) (setq size '( 51409 45 100 39 1.1 100 47)))
((= an1 51110) (setq size '( 51110 50 70 14 0.6 70 52)))
((= an1 51210) (setq size '( 51210 50 78 22 1.0 78 52)))
((= an1 51310) (setq size '( 51310 50 95 31 1.1 95 52)))
((= an1 51410) (setq size '( 51410 50 110 43 1.5 110 52)))
((= an1 51111) (setq size '( 51111 55 78 16 0.6 78 57)))
((= an1 51211) (setq size '( 51211 55 90 25 1.0 90 57)))
((= an1 51311) (setq size '( 51311 55 105 35 1.1 105 57)))
((= an1 51411) (setq size '( 51411 55 120 48 1.5 120 57)))
((= an1 51112) (setq size '( 51112 60 85 17 1.0 85 62)))
((= an1 51212) (setq size '( 51212 60 95 26 1.0 95 62)))
((= an1 51312) (setq size '( 51312 60 110 35 1.1 110 62)))
((= an1 51412) (setq size '( 51412 60 130 51 1.5 130 62)))
((= an1 51113) (setq size '( 51113 65 90 18 1.0 90 67)))
((= an1 51213) (setq size '( 51213 65 100 27 1.0 100 67)))
((= an1 51313) (setq size '( 51313 65 115 36 1.1 115 67)))
((= an1 51413) (setq size '( 51413 65 140 56 2.0 140 68)))
((= an1 51114) (setq size '( 51114 70 95 18 1.0 95 72)))
((= an1 51214) (setq size '( 51214 70 105 27 1.0 105 72)))
((= an1 51314) (setq size '( 51314 70 125 40 1.1 125 72)))
((= an1 51414) (setq size '( 51414 70 150 60 2.0 150 73)))
((= an1 51115) (setq size '( 51115 75 100 19 1.0 100 77)))
((= an1 51215) (setq size '( 51215 75 110 27 1.0 110 77)))
((= an1 51315) (setq size '( 51315 75 135 44 1.5 135 77)))
((= an1 51415) (setq size '( 51415 75 160 65 2.0 160 78)))
((= an1 51116) (setq size '( 51116 80 105 19 1.0 105 82)))
((= an1 51216) (setq size '( 51216 80 115 28 1.0 115 82)))
((= an1 51316) (setq size '( 51316 80 140 44 1.5 140 82)))
((= an1 51416) (setq size '( 51416 80 170 68 2.1 170 83)))
((= an1 51117) (setq size '( 51117 85 110 19 1.0 110 87)))
((= an1 51217) (setq size '( 51217 85 125 31 1.0 125 88)))
((= an1 51317) (setq size '( 51317 85 150 49 1.5 150 88)))
((= an1 51417) (setq size '( 51417 85 180 72 2.1 177 88)))
((= an1 51118) (setq size '( 51118 90 120 22 1.0 120 92)))
((= an1 51218) (setq size '( 51218 90 135 35 1.1 135 93)))
((= an1 51318) (setq size '( 51318 90 155 50 1.5 155 93)))
((= an1 51418) (setq size '( 51418 90 190 77 2.1 187 93)))
((= an1 51120) (setq size '( 51120 100 135 25 1.0 135 102)))
((= an1 51220) (setq size '( 51220 100 150 38 1.1 150 103)))
((= an1 51320) (setq size '( 51320 100 170 55 1.5 170 103)))
((= an1 51420) (setq size '( 51420 100 210 85 3.0 205 103)))
((= an1 51122) (setq size '( 51122 110 145 25 1.0 145 112)))
((= an1 51222) (setq size '( 51222 110 160 38 1.1 160 113)))
((= an1 51322) (setq size '( 51322 110 190 63 2.0 187 113)))
((= an1 51422) (setq size '( 51422 110 230 95 3.0 225 113)))
((= an1 51124) (setq size '( 51124 120 155 25 1.0 155 122)))
((= an1 51224) (setq size '( 51224 120 170 39 1.1 170 123)))
((= an1 51324) (setq size '( 51324 120 210 70 2.1 205 123)))
((= an1 51424) (setq size '( 51424 120 250 102 4.0 245 123)))
((= an1 51126) (setq size '( 51126 130 170 30 1.0 170 132)))
((= an1 51226) (setq size '( 51226 130 190 45 1.5 187 133)))
((= an1 51326) (setq size '( 51326 130 225 75 2.1 220 134)))
((= an1 51426) (setq size '( 51426 130 270 110 4.0 265 134)))
((= an1 51128) (setq size '( 51128 140 180 31 1.0 178 142)))
((= an1 51228) (setq size '( 51228 140 200 46 1.5 197 143)))
((= an1 51328) (setq size '( 51328 140 240 80 2.1 235 144)))
((= an1 51428) (setq size '( 51428 140 280 112 4.0 275 144)))
((= an1 51130) (setq size '( 51130 150 190 31 1.0 188 152)))
((= an1 51230) (setq size '( 51230 150 215 50 1.5 212 153)))
((= an1 51330) (setq size '( 51330 150 250 80 2.1 245 154)))
((= an1 51430) (setq size '( 51430 150 300 120 4.0 295 153)))
((= an1 51132) (setq size '( 51132 160 200 31 1.0 198 162)))
((= an1 51232) (setq size '( 51232 160 225 51 1.5 222 163)))
((= an1 51332) (setq size '( 51332 160 270 87 3.0 265 164)))
((= an1 51432) (setq size '( 51432 160 320 130 5.0 315 164)))
((= an1 51134) (setq size '( 51134 170 215 34 1.1 213 172)))
((= an1 51234) (setq size '( 51234 170 240 55 1.5 237 173)))
((= an1 51334) (setq size '( 51334 170 280 87 3.0 275 174)))
((= an1 51434) (setq size '( 51434 170 340 135 5.0 335 174)))
((= an1 51136) (setq size '( 51136 180 225 34 1.1 222 183)))
((= an1 51236) (setq size '( 51236 180 250 56 1.5 247 183)))
((= an1 51336) (setq size '( 51336 180 300 95 3.0 295 184)))
((= an1 51436) (setq size '( 51436 180 360 140 5.0 355 184)))
((= an1 51138) (setq size '( 51138 190 240 37 1.1 237 193)))
((= an1 51238) (setq size '( 51238 190 270 62 2.0 267 194)))
((= an1 51338) (setq size '( 51338 190 320 105 4.0 315 195)))
((= an1 51140) (setq size '( 51140 200 250 37 1.1 247 203)))
((= an1 51240) (setq size '( 51240 200 280 62 2.0 277 204)))
((= an1 51340) (setq size '( 51340 200 340 110 4.0 335 205)))
((= an1 51144) (setq size '( 51144 220 270 37 1.1 267 223)))
((= an1 51244) (setq size '( 51244 220 300 63 2.0 297 224)))
((= an1 51148) (setq size '( 51148 240 300 45 1.5 297 243)))
((= an1 51248) (setq size '( 51248 240 340 78 2.1 335 244)))
((= an1 51152) (setq size '( 51152 260 320 45 1.5 317 263)))
((= an1 51252) (setq size '( 51252 260 360 79 2.1 355 264)))
((= an1 51156) (setq size '( 51156 280 350 53 1.5 347 283)))
((= an1 51256) (setq size '( 51256 280 380 80 2.1 375 284)))
((= an1 51160) (setq size '( 51160 300 380 62 2.0 376 304)))
((= an1 51260) (setq size '( 51260 300 420 95 3.0 415 304)))
((= an1 51164) (setq size '( 51164 320 400 63 2.0 396 324)))
((= an1 51264) (setq size '( 51264 320 440 95 3.0 435 325)))
((= an1 51168) (setq size '( 51168 340 420 64 2.0 416 344)))
((= an1 51268) (setq size '( 51268 340 460 96 3.0 455 345)))
((= an1 51172) (setq size '( 51172 360 440 65 2.0 436 364)))
((= an1 51272) (setq size '( 51272 360 500 110 4.0 495 365)))
)   ;;;bearing total:123ea
 (if (= size nil)
  (progn
    (princ "\nNot Exist Bearing No.!")
    (exit)
  )
 )  
(setq nd (nth 0 size)            ;brg no.
       d (nth 1 size)            ;brg top id
      o1 (nth 2 size)            ;brg btm od
     thk (nth 3 size)            ;brg height
       r (nth 4 size)            ;brg corner radius
      o2 (nth 5 size)            ;brg top od
      d1 (nth 6 size))           ;brg btm id
;
(setq t1 (/ thk 3.0)              ; t/3
      w1 (/ (- o1 d1) 2.0)
     dr1 (/ d1 2.0)
      w2 (/ (- o2 d) 2.0)
     dr2 (/ d 2.0)
      bd (+ t1 (* (/ t1 4.0) 2.0)))  ;ball dia.
(initget 1)
(setq pt (getpoint "\nPick bearing bottom center : " ))
(setq p1 (polar pt (dtr 180) dr1)
      p2 (polar p1 (dtr 180) w1)
      p3 (polar p2 (dtr 90) t1)
      p4 (polar p3 (dtr 0) w1)
     p21 (polar pt (dtr 90) thk)
      p8 (polar p21 (dtr 180) (/ o2 2.0))
      p5 (polar p8 (dtr 270) t1)
      p6 (polar p5 (dtr 0) w2)
      p7 (polar p6 (dtr 90) t1)
     p10 (polar pt (dtr 180) (+ (/ d1 2.0) (/ w1 2.0)))
      p9 (polar p10 (dtr 90) (/ thk 2.0))
     p11 (polar p4 (dtr 180) (/ w1 2.0))
     p12 (polar p11 (dtr 90) t1)
     p13 (polar p21 (dtr 0) (+ dr2 r))
     p14 (polar p13 (dtr 270) t1)
     p15 (polar p14 (dtr 180) (+ d (* r 2.0)))
     p16 (polar p15 (dtr 90) t1)
     p17 (polar p3 (dtr 0) (+ w1 d1 r))
     p18 (polar p17 (dtr 180) (+ d1 (* r 2.0)))
     p19 (polar p18 (dtr 270) t1)
     p20 (polar p17 (dtr 270) t1)
     p22 (polar p8 (dtr 270) (/ t1 2.0))
     p23 (polar p1 (dtr 90) (/ t1 2.0)))
(command "line" p6 p7 "") (setq ep1 (entlast)) 
(command "line" p7 p8 "") (setq ep2 (entlast))
(command "line" p8 p5 "") (setq ep3 (entlast))
(command "line" p5 p6 "") (setq ep4 (entlast))
(command "line" p1 p4 "") (setq ep5 (entlast))
(command "line" p4 p3 "") (setq ep6 (entlast))
(command "line" p3 p2 "") (setq ep7 (entlast))
(command "line" p2 p1 "") (setq ep8 (entlast))
(command "circle" p9 "d" bd) (setq ep9 (entlast))
(command "fillet" "r" r)
(command "fillet" ep1 ep2) (setq f1 (entlast))
(command "fillet" ep2 ep3) (setq f2 (entlast))
(command "fillet" ep3 ep4) (setq f3 (entlast))
(command "fillet" ep4 ep1) (setq f4 (entlast))
(command "fillet" ep5 ep6) (setq f5 (entlast))
(command "fillet" ep6 ep7) (setq f6 (entlast))
(command "fillet" ep7 ep8) (setq f7 (entlast))
(command "fillet" ep8 ep5) (setq f8 (entlast))
  
(command "pedit" ep1 "" "j" ep1 f1 ep2 f2 ep3 f3 ep4 f4 "" "") (setq f9 (entlast))
(command "pedit" ep5 "" "j" ep5 f5 ep6 f6 ep7 f7 ep8 f8 "" "") (setq f10 (entlast))  
(command "trim" ep9 "" "f" p11 p12 "" "") (setq ep10 (entlast))
(command "mirror" f9 "" p21 pt "")   (setq f13 (entlast))
(command "mirror" f10 "" p21 pt "")  (setq f14 (entlast))
(command "mirror" ep9 "" p21 pt "")  (setq f16 (entlast))  
(command "mirror" ep9 "" p21 pt "") (setq f15 (entlast))  
(command "rotate" f9 f10 ep9 f15 f13 f14 f15 f16 "" pt "\\")
(setvar "pdmode" opd)  
(command "point" pt)  
 ;(command "line" p16 p13 "") 
 ;(command "line" p15 p14 "") 
 ;(command "line" p18 p17 "") 
 ;(command "line" p19 p20 "") 
(princ (strcat "\nYou select: " (rtos an1) " (" (rtos d) "x" (rtos o1)
                              "x" (rtos thk) "H) -- Ball dia is not real size."))
)
);end if -thrust brg.  
;-------------------------------------------------------------------------------------
(if (= ans 3)
 (progn
(initget 7)
(setq an1 (getint "\nShaft Dia. : " ))
(cond
((= an1 15)  (setq size '( 15 02 25 21 21 4 2 15.5 5 0.4 1 13.5 4 1 28 13)))
((= an1 17)  (setq size '( 17 03 28 24 24 4 2 17.5 5 0.4 1 15.5 4 1 32 13)))
((= an1 20)  (setq size '( 20 04 32 26 28 4 2 20.5 6 0.4 1 18.5 4 1 36 13)))
((= an1 25)  (setq size '( 25 05 38 32 34 5 2 25.8 7 0.4 1.5 23 5 1.2 42 13)))
((= an1 30)  (setq size '( 30 06 45 38 41 5 2 30.8 7 0.4 1.5 27.5 5 1.2 49 13)))
((= an1 35)  (setq size '( 35 07 52 44 48 5 2 35.8 8 0.4 1.5 32.5 6 1.2 57 15)))
((= an1 40)  (setq size '( 40 08 58 50 53 6 2.5 40.8 9 0.5 1.5 37.5 6 1.2 62 15)))
((= an1 45)  (setq size '( 45 09 65 56 60 6 2.5 45.8 10 0.5 1.5 42.5 6 1.2 69 17)))
((= an1 50)  (setq size '( 50 10 70 61 65 6 2.5 50.8 11 0.5 1.5 47.5 6 1.2 74 17)))
((= an1 55)  (setq size '( 55 11 75 67 69 7 3 56 11 0.5 2 52.5 8 1.2 81 17)))
((= an1 60)  (setq size '( 60 12 80 73 74 7 3 61 11 0.5 2 57.5 8 1.5 86 17)))
((= an1 65)  (setq size '( 65 13 85 79 79 7 3 66 12 0.5 2 62.5 8 1.5 92 19)))
((= an1 70)  (setq size '( 70 14 92 85 85 8 3.5 71 12 0.5 2 66.5 8 1.5 98 19)))
((= an1 75)  (setq size '( 75 15 98 90 91 8 3.5 76 13 0.5 2 71.5 8 1.5 104 19)))
((= an1 80)  (setq size '( 80 16 105 95 98 8 3.5 81 15 0.6 2 76.5 10 1.8 112 19)))
((= an1 85)  (setq size '( 85 17 110 102 103 8 3.5 86 16 0.6 2 81.5 10 1.8 119 19)))
((= an1 90)  (setq size '( 90 18 120 108 112 10 4 91 16 0.6 2 86.5 10 1.8 126 19)))
((= an1 95)  (setq size '( 95 19 125 113 117 10 4 96 17 0.6 2 91.5 10 1.8 133 19)))
((= an1 100) (setq size '( 100 20 130 120 122 10 4 101 18 0.6 2 96.5 12 1.8 142 19)))
((= an1 105) (setq size '( 105 21 140 126 130 12 5 106 18 0.7 2 100.5 12 1.8 145 19)))
((= an1 110) (setq size '( 110 22 145 133 135 12 5 111 19 0.7 2 105.5 12 1.8 154 19)))
((= an1 115) (setq size '( 115 23 150 137 140 12 5 116 19 0.7 2 110.5 12 2 159 19)))
((= an1 120) (setq size '( 120 24 155 138 145 12 5 121 20 0.7 2 115 14 2 164 19)))
((= an1 125) (setq size '( 125 25 160 148 150 12 5 126 21 0.7 2 120 14 2 170 19)))
((= an1 130) (setq size '( 130 26 165 149 155 12 5 131 21 0.7 2 125 14 2 175 19)))
((= an1 135) (setq size '( 135 27 175 160 163 14 6 136 22 0.7 2 130 14 2 185 19)))
((= an1 140) (setq size '( 140 28 180 160 168 14 6 141 22 0.7 2 135 16 2 192 19)))
((= an1 145) (setq size '( 145 29 190 172 178 14 6 146 24 0.7 2 140 16 2 202 19)))
((= an1 150) (setq size '( 150 30 195 171 183 14 6 151 24 0.7 2 145 16 2 205 19)))
((= an1 155) (setq size '( 155 31 200 182 186 16 7 156.5 25 0.7 3 147.5 16 2.5 212 19)))
((= an1 160) (setq size '( 160 32 210 182 196 16 7 161.5 25 0.7 3 154 18 2.5 217 )))
((= an1 165) (setq size '( 165 33 210 193 196 16 7 166.5 26 0.7 3 157.5 18 2.5 222 )))
((= an1 170) (setq size '( 170 34 220 193 206 16 7 171.5 26 0.7 3 164 18 2.5 232 )))
((= an1 180) (setq size '( 180 36 230 203 214 18 8 181.5 27 0.7 3 174 20 2.5 242 )))
((= an1 190) (setq size '( 190 38 240 214 224 18 8 191.5 28 0.7 3 184 20 2.5 252 )))
((= an1 200) (setq size '( 200 40 250 226 234 18 8 201.5 29 0.7 3 194 20 2.5 262 )))
)
 (if (= size nil)
  (progn
    (princ "\nNot Exist !")
    (exit)
  )
 )   
(setq d1 (nth 0 size)            
      nd (nth 1 size)            
      d3 (nth 2 size)            
      d4 (nth 3 size)           
       g (nth 4 size)           
       s (nth 5 size)           
       thk (nth 6 size)           
      d6 (nth 7 size)
      bn (nth 8 size)
       r (nth 9 size)
      ph (nth 10 size)
       k (nth 11 size)
       e (nth 12 size)
      tk (nth 13 size)
      d5 (nth 14 size)
       z (nth 15 size))
(setq d2 (- d1 (* 1.082532 ph))
      x1 (/ (- d3 d4) 2.0)
      l1 (/ x1 (cos (dtr 30.0)))
      x2 (/ (- d6 d2) 2.0))
(initget "e p w") 
(setq ans (strcase (getkword"\ndraw [Elevation/Plan/Washer] : " )T))
(if (= ans "e")
(progn
(initget "l r")
(setq rl (strcase (getkword "\npick point <Left/Right> : " )T))
(initget 1)
(setq pt (getpoint "\nPick shaft center"))
(setq p1 (polar pt (dtr 180) bn)
      p2 (polar pt (dtr 90) (/ d2 2.0))
      p3 (polar pt (dtr 90) (/ d6 2.0))
      p4 (polar p2 (dtr 180) x2)
      p5 (polar p2 (dtr 180) (- bn x2))
      p6 (polar p3 (dtr 180) bn)
      p7 (polar pt (dtr 90) (/ d1 2.0))
      p8 (polar p7 (dtr 180) bn)
      p9 (polar pt (dtr 90) (/ d4 2.0))  
     p10 (polar p9 (dtr 120) l1)
     p11 (polar p1 (dtr 90) (/ d3 2.0))
     p12 (polar p1 (dtr 90) (/ g 2.0))
     p13 (polar pt (dtr 90) (/ g 2.0))
     p14 (polar p6 (dtr 270) d6)
     p15 (polar p3 (dtr 270) d6)
      rc (polar p1 (dtr 0) (/ bn 2.0)))
(command "line" p4 p3 "")  (setq ep1 (entlast))
(command "line" p3 p9 "")  (setq ep2 (entlast))
(command "line" p9 p10 "") (setq ep3 (entlast))
(command "line" p10 p11 "")(setq ep4 (entlast))
(command "line" p11 p6 "") (setq ep5 (entlast))
(command "line" p6 p5 "")  (setq ep6 (entlast))
(command "line" p5 p4 "")  (setq ep7 (entlast))
(command "line" p12 p13 "")(setq ep8 (entlast))
(command "trim" ep3 ep2 "" p13 "")   (setq ep9 (entlast))
(command "line" p8 p7 "")            (setq ep10 (entlast))         
(command "trim" ep6 ep1 "" p8 p7 "") (setq ep11 (entlast))         
(command "pedit" ep1 "" "j" ep1 ep2 ep3 ep4 ep5 ep6 ep7 "" "")
(setq ep12 (entlast))
(command "mirror" ep11 "" pt p1 "")  (setq ep13 (entlast))
(command "mirror" ep9 "" pt p1 "")   (setq ep14 (entlast)) 
(command "mirror" ep12 "" pt p1 "")  (setq ep15 (entlast)) 
(command "line" p6 p14 "")  (setq ep16 (entlast))
(command "line" p3 p15 "")  (setq ep17 (entlast))
(if (= rl "l")      
(progn
(command "mirror" ep12 ep8 ep10 ep13 ep14 ep15 ep16 ep17 "" p3 p15 "y"   
         "redraw")
)
)
(princ (strcat "\nYou select:   AN " (rtos nd) " -  M" (rtos d1) 
                                   "xp" (rtos ph) " - " (rtos d1) "dia."))
);progn
);if
;--------------nut plan
(if (= ans "p")
(progn
(initget 1)
(setq pt (getpoint "\nPick nut center"))
(setq p1 (polar pt (dtr 90) (- (/ d3 2.0) thk))
      p2 (polar p1 (dtr 180) (/ s 2.0))
      p3 (polar p2 (dtr 0) s)
      p4 (polar p2 (dtr 90) thk)
      p5 (polar p4 (dtr 0) s)
      p6 (polar pt (dtr 90) (/ d3 2.0))
      p7 (polar pt (dtr 180) (/ d3 2.0))
      p8 (polar p7 (dtr 90) (/ s 2.0)) 
      p9 (polar p8 (dtr 0) thk) 
     p10 (polar pt (dtr 0) (/ d1 2.0))) 
(command "circle" pt "d" d3)  (setq ep1 (entlast))
(command "line" p4 p2 "")     (setq ep2 (entlast))
(command "line" p2 p3 "")     (setq ep3 (entlast))
(command "line" p3 p5 "")     (setq ep4 (entlast))
(command "trim" ep1 "" p4 "") (setq ep5 (entlast)) 
(command "trim" ep1 "" p5 "") (setq ep6 (entlast))
(command "fillet" "r" r)
(command "fillet" ep2 ep3)    (setq ep9 (entlast))
(command "fillet" ep3 ep4)    (setq ep10 (entlast))
(command "array" ep2 ep3 ep4 ep9 ep10 "" "p" pt "4" "" "")
(command "line" p8 p9 "")     (setq ep7 (entlast))
(command "line" p2 p4 "")     (setq ep8 (entlast)) 
(command "trim" ep8 ep7 "" p7 ""  
         "erase" ep7 ep8 ""
         "redraw"
         "array" ep1 "" "p" pt "4" "" ""
         "circle" pt "d" d2
         "circle" pt "d" d1
         "circle" pt "d" d4)
(princ (strcat "\nYou select:   AN " (rtos nd) " -  M" (rtos d1) 
                                   "xp" (rtos ph) " - " (rtos d1) "dia."))
);progn
);if
;============== Washer
(if (= ans "w") 
(progn
(initget "e p")
(setq an2 (strcase (getkword"\ndraw washer [Elevation/Plan] : " )T))
(if (= an2 "p")  ;;plan
(progn 
(setq de1 (/ (/ s 2.0) (/ d4 2.0))  ;sin
      de2 (- 90.0 (* (/ 180 pi) (atan (sqrt (- 1 (expt de1 2))) de1))) ;arcs
      dg1 (dtr de2)
      dg2 (/ (dtr 360) z) 
      dg3 (- dg2 (* dg1 2.0)))
(initget 1)
(setq pt (getpoint "\nPick washer center"))
(setq p1 (polar pt (dtr 90) (/ d1 2.0))
      po (polar p1 (dtr 270) (- d1 k)) 
      p2 (polar pt (dtr 90) (/ d5 2.0)) 
      p3 (polar p2 (dtr 180) (/ s 2.0)) 
      p4 (polar p3 (dtr 0) s) 
      p5 (polar pt (+ (dtr 90) dg1) (/ d4 2.0)) 
      p6 (polar p5 (dtr 0) s)
      p7 (polar pt (+ (dtr 90) (+ dg1 dg3)) (/ d4 2.0))
      p8 (polar p1 (dtr 180) (/ e 2.0))
      p9 (polar po (dtr 180) (/ e 2.0))
     p10 (polar p9 (dtr 0) e) 
     p11 (polar pt (dtr 180) (/ d5 2.0))
     p12 (polar p8 (dtr 0) e)) 
(command "circle" pt "d" d5)       (setq ep1 (entlast))
(command "line" p3 p5 "")          (setq ep2 (entlast))
(command "line" p4 p6 "")          (setq ep3 (entlast))
(command "trim" ep2 ep3 "" p11 "") (setq ep4 (entlast)) 
(command "trim" ep1 "" p3 "")      (setq ep5 (entlast))
(command "trim" ep1 "" p4 "")      (setq ep6 (entlast))
(command "arc" "c" pt p5 p7)       (setq ep7 (entlast))
(command "mirror" ep7 "" p1 pt "") (setq ep8 (entlast))
(command "array" ep1 ep2 ep3 ep7 ep8 "" "p" pt z "" "") 
(command "circle" pt "d" d1)       (setq ep9 (entlast)) 
(command "line" p8 p9 "")          (setq ep10 (entlast))
(command "line" p12 p10 "")        (setq ep11 (entlast))
(command "trim" ep10 ep11 "" p1 "" 
         "trim" ep9 "" p8 p12 ""
         "line" p9 p10 "")
(princ (strcat "\nYou select:   AW " (rtos nd) " -  M" (rtos d1) 
                                   "xp" (rtos ph) " - " (rtos d1) "dia."))
);progn (plan)
);if    (plan)
;------------------ elevation
(if (= an2 "e")  
(progn 
(setq  h1 (* tk (sin (dtr 25)))
       h2 (/ (- (- d5 (* h1 2.0)) d4) 2.0)
      le1 (/ h2 (cos (dtr 25))))
(initget "l r")
(setq rl (strcase (getkword "\npick point <Left/Right> : " )T))
(initget 1)
(setq pt (getpoint "\nPick shaft center"))
;(if (= rl "l")      
;(progn
;(setq po (polar pt (dtr 180) (* tk 2.0))   
;      pt po) 
;)
;)
(setq po (polar pt (dtr 180) tk)
      p1 (polar po (dtr 90) (/ d4 2.0))
      p2 (polar p1 (+ (dtr 90) (dtr 25)) le1)
      p3 (polar p2 (dtr 25) tk)
      p4 (polar p1 (dtr 270) d4)
      p5 (polar p2 (dtr 270) (- d5 (* h1 2.0)))
      p6 (polar po (dtr 90) (/ d1 2.0))
      p7 (polar p6 (dtr 0) tk))
(command "pline" p2 p1 p4 p5 "")   (setq ep1 (entlast))
(command "offset" tk p1 pt "")     (setq ep2 (entlast))
(command "line" p2 p3 "")          (setq ep3 (entlast))
(command "line" p6 p7 "")          (setq ep4 (entlast))
(command "mirror" ep3 "" po pt "") (setq ep5 (entlast)) 
(command "mirror" ep4 "" po pt "") (setq ep6 (entlast))
(command "pedit" ep2 "j" ep3 ep1 ep5 "" "") (setq ep7 (entlast))
(if (= rl "l")      
(progn
(command "mirror" ep7 ep4 ep6 "" p7 pt "y"   
         "redraw")
)
)
(princ (strcat "\nYou select:   AW " (rtos nd) " -  M" (rtos d1) 
                                   "xp" (rtos ph) " - " (rtos d1) "dia."))
);progn (w.elev)
);if    (w.elev)
);progn (washer)
);if    (washer)
)
);end if -lock&nut  
;------------------------------------------------------------------------------------
(if (= ans 4)
 (progn 
  (textpage)
  (princ "\n                        [ UCP BEARING BLOCK]                        ")
(princ "\n====================================================================")
(princ "\n  1. UCP201-12d    2. UCP202-15d    3. UCP203-17d    4. UCP204-20d ")
(princ "\n  5. UCP205-25d    6. UCP305-25d    7. UCPX05-25d    8. UCP206-30d ")
(princ "\n  9. UCP306-30d   10. UCPX06-30d   11. UCP207-35d   12. UCP307-35d ")
(princ "\n 13. UCPX07-35d   14. UCP208-40d   15. UCP308-40d   16. UCPX08-40d ")
(princ "\n 17. UCP209-45d   18. UCP309-45d   19. UCPX09-45d   20. UCP210-50d ")  
(princ "\n 21. UCP310-50d   22. UCPX10-50d   23. UCP211-55d   24. UCP311-55d ")
(princ "\n 25. UCPX11-55d   26. UCP212-60d   27. UCP312-60d   28. UCPX12-60d ")  
(princ "\n 29. UCP213-65d   30. UCP313-65d   31. UCPX13-65d   32. UCP214-70d ")
(princ "\n 33. UCP314-70d   34. UCPX14-70d   35. UCP215-75d   36. UCP315-75d ")
(princ "\n 37. UCPX15-75d   38. UCP216-80d   39. UCP316-80d   40. UCPX16-80d ")  
(princ "\n 41. UCP217-85d   42. UCP317-85d   43. UCPX17-85d   44. UCP218-90d ")
(princ "\n 45. UCP318-90d   46. UCPX18-90d   47. UCP319-95d   48. UCP320-100d ")
(princ "\n 49. UCPX20-100d  50. UCP321-105d  51. UCP322-110d  52. UCP324-120d ")
(princ "\n 53. UCP326-130d  54. UCP328-140d                   * d=shaft dia.  ")
(princ "\n====================================================================")
(initget 7)
(setq an1 (getint "\nBearing No.?  : " ))
(cond
((= an1 1)  (setq size '(12 47 18 1.0 12.7 18.3 4.5 6.0 0.75  
                         127 38 95 15 30.2 13 19 62 10 0.7 "201")))
((= an1 2)  (setq size '(15 47 18 1.0 12.7 18.3 4.5 6.0 0.75  
                         127 38 95 15 30.2 13 19 62 10 0.69 "202")))
((= an1 3)  (setq size '(17 47 18 1.0 12.7 18.3 4.5 6.0 0.75  
                         127 38 95 15 30.2 13 19 62 10 0.68 "203")))
((= an1 4)  (setq size '(20 47 18 1.5 12.7 18.3 4.5 6.0 0.75 
                         127 38 95 15 33.3 13 19 65 10 0.68 "204")))
((= an1 5)  (setq size '(25 52 20 1.5 14.3 19.7 5.0 6.0 0.75  
                         140 38 105 16 36.5 13 19 70 10 0.82 "205")))
((= an1 6)  (setq size '(25 62 24 2.0 15.0 23.0 6.0 6.0 0.75  
                         175 45 132 16 45 17 20 83 14 1.32 "305")))
((= an1 7)  (setq size '(25 62 22 1.5 15.9 22.2 5.0 6.0 0.75  
                         159 51 119 16 44.4 17 21 83 14 1.31 "X05")))
((= an1 8)  (setq size '(30 62 22 1.5 15.9 22.2 5.0 6.0 0.75  
                         165 48 121 18 42.9 17 21 83 14 1.36 "206")))
((= an1 9)  (setq size '(30 72 26 2.0 17.0 26.0 6.0 6.0 0.75 
                         180 50 140 19 50 17 20 94 14 1.82 "306")))
((= an1 10) (setq size '(30 72 24 1.5 17.5 25.4 6.0 8.0 1.00  
                         175 57 127 18 47.6 17 21 93 14 1.86 "X06")))
((= an1 11) (setq size '(35 72 24 2.0 17.5 25.4 6.0 8.0 1.00  
                         167 48 127 19 47.6 17 21 94 14 1.73 "207")))
((= an1 12) (setq size '(35 80 28 2.5 19.0 29.0 8.0 8.0 1.00  
                         210 56 160 21 56 17 25 105 14 2.5 "307")))
((= an1 13) (setq size '(35 80 26 2.0 19.0 30.2 8.0 8.0 1.00  
                         203 57 144 19 54 17 26 104 14 2.4 "X07")))
((= an1 14) (setq size '(40 80 26 2.0 19.0 30.2 8.0 8.0 1.00  
                         184 54 137 19 49.2 17 23 100 14 2.1 "208")))
((= an1 15) (setq size '(40 90 30 2.5 19.0 33.0 10 10 1.25  
                         220 60 170 23 60 17 27 116 14 3.2 "308")))
((= an1 16) (setq size '(40 85 28 2.0 19.0 30.2 8.0 8.0 1.00  
                         222 67 156 21 58.7 20 28 112 16 3.0 "X08")))
((= an1 17) (setq size '(45 85 28 2.0 19.0 30.2 8.0 8.0 1.00  
                         190 54 146 20 54 17 23 108 14 2.3 "209")))
((= an1 18) (setq size '(45 100 33 2.5 22 35 10 10 1.25  
                         245 67 190 25 67 20 30.0 128 16 4.3 "309")))
((= an1 19) (setq size '(45 90 29 2.0 19 32.6 9 10 1.25  
                         222 67 156 22 58.7 20 29 115 16 3.2 "X09")))
((= an1 20) (setq size '(50 90 29 2.0 19 32.6 9 10 1.25  
                         206 60 159 22 57.2 20 25 114 16 2.7 "210")))
((= an1 21) (setq size '(50 110 35 3.0 22 39 12 12 1.50  
                         275 75 212 28 75 20 35 143 16 5.8 "310")))
((= an1 22) (setq size '(50 100 33 2.0 22.2 33.4 9 10 1.25  
                         241 73 171 25 63.5 20 30 126 16 4.2 "X10")))
((= an1 23) (setq size '(55 100 33 2.5 22.2 33.4 9 10 1.25  
                         219 60 171 22 63.5 20 25 126 16 3.4 "211")))
((= an1 24) (setq size '(55 120 37 3.0 25 41 12 12 1.5  
                         310 80 236 31 80 20 38 154 16 7.4 "311")))
((= an1 25) (setq size '(55 110 36 2.5 25.4 39.7 10 10 1.25  
                         260 79 184 28 69.8 25 30 139 20 5.6 "X11")))
((= an1 26) (setq size '(60 110 36 2.5 25.4 39.7 9.0 10 1.25  
                         241 70 184 25 69.8 20 25 138 16 4.8 "212")))
((= an1 27) (setq size '(60 130 39 3.5 26 45 12 12 1.5  
                         330 85 250 33 85 25 38 165 20 9.0 "312")))
((= an1 28) (setq size '(60 120 39 2.5 25.4 39.7 10 10 1.25  
                         286 83 203 30 76.2 25 35 151 20 6.9 "X12")))
((= an1 29) (setq size '(65 120 39 2.5 25.4 39.7 10 10 1.25  
                         265 70 203 27 76.2 25 29 150 20 5.7 "213")))
((= an1 30) (setq size '(65 140 41 3.5 30 45 12 12 1.5  
                         340 90 260 36 90 25 38 174 20 10.2 "313")))
((= an1 31) (setq size '(65 125 40 2.5 30.2 44.4 12 12 1.5  
                         286 83 203 31 76.2 25 35 154 20 7.4 "X13")))
((= an1 32) (setq size '(70 125 40 2.5 30.2 44.4 12 12 1.5  
                         266 72 210 27 79.4 25 31 156 20 6.4 "214")))
((= an1 33) (setq size '(70 150 43 3.5 33 45 12 12 1.5  
                         360 90 280 40 95 27 40 186 22 12.4 "314")))
((= an1 34) (setq size '(70 130 42 2.5 33.3 44.5 12 12 1.5  
                         330 89 229 32 88.9 27 39 170 22 9.1 "X14")))
((= an1 35) (setq size '(75 130 42 2.5 33.3 44.5 12 12 1.5  
                         275 74 217 28 82.6 25 31 163 20 7.2 "215")))
((= an1 36) (setq size '(75 160 46 3.5 32 50 14 14 1.5  
                         380 100 290 40 100 27 40 197 22 14.6 "315")))
((= an1 37) (setq size '(75 140 45 2.5 33.3 49.3 12 12 1.5  
                         330 89 229 35 88.9 27 39 175 22 10.3 "X15")))
((= an1 38) (setq size '(80 140 45 3.0 33.3 49.3 12 12 1.5  
                         292 78 232 30 88.9 25 31 175 20 8.7 "216")))
((= an1 39) (setq size '(80 170 48 3.5 34 52 14 14 1.5  
                         400 110 300 45 106 27 40 209 22 18.1 "316")))
((= an1 40) (setq size '(80 150 48 3.0 34.1 51.6 12 12 1.5  
                         381 102 283 38 101.6 27 54 196 22 14 "X16")))
((= an1 41) (setq size '(85 150 48 3.0 34.1 51.6 12 12 1.5  
                         310 83 247 32 95.2 25 31 187 20 11 "217")))
((= an1 42) (setq size '(85 180 50 4.0 40 56 16 16 1.5  
                         420 110 320 45 112 33 45 221 27 21 "317")))
((= an1 43) (setq size '(85 160 51 3.0 39.7 56.3 12 12 1.5  
                         381 102 283 40 101.6 27 54 202 22 15.6 "X17")))
((= an1 44) (setq size '(90 160 51 3.0 39.7 56.3 12 12 1.5  
                         327 88 262 34 101.6 27 33 200 22 13.3 "218")))
((= an1 45) (setq size '(90 190 52 4.0 40 56 16 16 1.5  
                         430 110 330 50 118 33 45 233 27 23 "318")))
((= an1 46) (setq size '(90 170 53 3.0 39.7 56.3 12 12 1.5  
                         381 111 283 42 101.6 27 54 208 22 17.8 "X18")))
((= an1 47) (setq size '(95 200 54 4.0 41 62 16 16 1.5  
                         470 120 360 50 125 36 50 250 30 29 "319")))
((= an1 48) (setq size '(100 215 58 4.0 42 62 18 18 1.5  
                         490 120 380 55 140 36 50 275 30 36 "320")))
((= an1 49) (setq size '(100 190 58 3.5 49.2 68.3 16 16 1.5  
                         432 121 337 48 127 33 58 246 27 26 "X20")))
((= an1 50) (setq size '(105 225 60 4.0 44 68 18 18 1.5  
                         490 120 380 55 140 36 50 278 30 36 "321")))
((= an1 51) (setq size '(110 240 62 4.0 46 71 18 18 1.5  
                         520 140 400 60 150 40 55 295 33 45 "322")))
((= an1 52) (setq size '(120 260 66 4.0 51 75 18 18 1.5  
                         570 140 450 70 160 40 55 321 33 61 "324")))
((= an1 53) (setq size '(130 300 76 5.0 59 86 20 20 1.5  
                         600 140 480 80 180 40 55 354 33 75 "326")))
((= an1 54) (setq size '(140 300 76 5.0 59 86 20 20 1.5  
                         620 140 500 80 200 40 55 388 33 91 "328")))
) ;cond
 (if (= size nil)
  (progn
    (princ "\nNot Exist !")
    (exit)
  )
 )    
;
(setq d (nth 0 size)       ;shaft dia
     do (nth 1 size)       ;outer dia     
     be (nth 2 size)       ;outer width     
      r (nth 3 size)       ;boss fillet     
      m (nth 4 size)       ;boss L-end     
      n (nth 5 size)       ;boss R-end
      g (nth 6 size)       ;boss tap distance     
     m1 (nth 7 size)       ;boss tap dia     
      p (nth 8 size)       ;boss tap pitch       
      l (nth 9 size)       ;ucp length     
      a (nth 10 size)      ;ucp width     
      j (nth 11 size)      ;setting bolt distance     
     h1 (nth 12 size)      ;ucp base thickness    
      h (nth 13 size)      ;base to shaft cen.     
     n1 (nth 14 size)      ;setting hole dia      
     n2 (nth 15 size)      ;setting slot hole length      
     h2 (nth 16 size)      ;base to top      
     m2 (nth 17 size)      ;setting bolt dia(Metric)      
      w (nth 18 size)      ;weight(kg)       
     nd (nth 19 size))     ;nominal name
;;;;;;;;;;;;;;;;;;;;;;;;;;;;;;;;;;;;;;;;;;;;;;;;;;;;
(setq gd (- m1 (* 1.082532 p))   ;boss tap gol-dia.
      of (/ (- m1 gd) 2.0)
     dor (/ do 2.0)
     beh (/ be 2.0) 
     dgo (/ beh dor)   
     dg1 (- 90.0 (* (/ 180.0 pi)(atan (sqrt (- 1 (expt dgo 2.0))) dgo))) ;arcsin deg
     dg2 (- (dtr dg1) (dtr 2.5))  ;;;;
      h3 (sqrt (- (expt dor 2.0) (expt beh 2.0)))
      l1 (- h2 h)
     wh1 (* (sin dg2) l1)
       tt (/ (- dor (/ d 2.0)) 3.0)
      br (/ (/ tt 2.0) (sin (dtr 30.0)))  ;ball dia
      bd (+ d (* tt 2.0))                 ;boss dia
      h4 (+ (/ bd 2.0) (/ tt 2.0))        ;ball location
       b (/ (- l j) 2.0)
       c (+ (/ n2 2.0) (* b 1.0))
      sh (- n2 n1))                      ;slot cen to cen
;;;;;;;;;;;;;;;;;;;;;;;;;;;;;;;;;;;;;;;;;;;;;;;;;;;;;;;;;;;;;;;;;;;
(graphscr)
(initget 1 "e t f")
(setq an2 (strcase (getkword "\ndraw <Elevation/Top/Front> : " )T))
(if (= an2 "e")    ;Elevation
(progn
(initget 1)
(setq po (getpoint "\nPick!  UCP left center: " ))
(setq p1 (polar po (dtr 0) m)
      p2 (polar p1 (dtr 90.0) (/ bd 2.0))
      p3 (polar p2 (dtr 180.0) m)
      p4 (polar p3 (dtr 270.0) tt)
      p5 (polar p4 (dtr 0) (+ m n))
      p6 (polar p5 (dtr 90.0) tt)
      p7 (polar p6 (dtr 180.0) g)
      p8 (polar p7 (dtr 90.0) 2.5)
      p9 (polar p7 (dtr 270.0) (+ tt 2.5))
     p10 (polar p7 (dtr 0) (/ m1 2.0))
     p11 (polar p10 (dtr 270.0) tt)
     p12 (polar p1 (dtr 90.0) h4)
     p13 (polar p2 (dtr 90.0) tt)
     p14 (polar p13 (dtr 0) beh)
     p15 (polar p14 (dtr 180.0) be)   
     p16 (polar p1 (dtr 90.0) h3)
     p17 (polar p16 (dtr 0) beh)
     p18 (polar p16 (dtr 180.0) beh) 
    p18a (polar p2 (dtr 0) beh)
     p19 (polar p1 (dtr 90.0) dor)
     p20 (polar p19 (dtr 0) beh)
     p21 (polar p20 (dtr 30.0) 0.5)   
     p22 (polar p1 (- (dtr 90.0) dg2) l1)     
     p23 (polar p1 (dtr 0.0) m)
     p24 (polar p7 (dtr 0.0) (/ gd 2.0))   
     p25 (polar p1 (dtr 90.0) l1)
     p26 (polar p1 (+ (dtr 90.0) dg2) l1)     
     p27 (polar p1 (dtr 270.0) h)   
     p28 (polar p27 (dtr 180.0) (/ a 2.0))
     p29 (polar p28 (dtr 0) a)
     p30 (polar p29 (dtr 90.0) h1)
     p31 (polar p30 (dtr 180.0) a)
     p32 (polar p27 (dtr 180.0) (/ n1 2.0))
     p33 (polar p32 (dtr 90.0) h1)   
     p34 (polar p1 (dtr 0) n)
     p35 (polar p34 (dtr 270.0) (/ bd 2.0))
     p36 (polar p35 (dtr 180.0) n)
     p37 (polar p24 (dtr 270.0) tt)      
     p38 (polar p25 (dtr 90.0) 2.5)
     p39 (polar p27 (dtr 270.0) 2.5)   
     p40 (polar po (dtr 180.0) 5.0)
     p41 (polar po (dtr 0) (+ (+ m n) 5.0))   
     p42 (polar p12 (dtr 180.0) (+ br 1.5))
     p43 (polar p12 (dtr 0.0) (+ br 1.5))
     p44 (polar p31 (dtr 0.0) (* r 1.6)) 
     p45 (polar p30 (dtr 180.0) (* r 1.6)) 
     p46 (polar p28 (dtr 90.0) h2))   
;;;;;;;;
(command "zoom" "w" p46 p29)
(command "line" p33 p32 "")              (setq e1 (entlast))
(command "line" p30 p31 p28 p29 p30 "") 
(command "mirror" e1 "" p36 p27 "")      (setq e2 (entlast))
(command "line" p6 p3 "")                (setq e3 (entlast))
(command "line" p3 p4 "")                (setq e4 (entlast))
(command "line" p4 p5 "")                (setq e5 (entlast))
(command "line" p5 p6 "")                (setq e6 (entlast))
(command "fillet" "r" r
         "fillet" e4 e5  
         "fillet" e5 e6)   
(command "line" p10 p11 "")              (setq e7 (entlast))
(command "line" p24 p37 "")              (setq e8 (entlast))
(command "mirror" e7 e8 "" p8 p7 "") 
(command "arc" p22 p25 p26)              (setq e8a (entlast))
(command "arc" p17 p19 p18)
(command "line" p22 p23 "")              (setq e9 (entlast))
(command "line" po p26 "")               (setq e9a (entlast))
(command "trim" e3 "" p23 po "")            
(command "fillet" "r" r
         "fillet" e3 e4
         "fillet" e3 e6)
(command "arc" p23 "e" p45 "d" "270")    (setq e10 (entlast))
(command "line" p15 p14 "")                    
(command "circle" p12 br)                (setq e11 (entlast)) 
(command "trim" e11 "" p13 ""
         "trim" e11 "" p2 "")
(command "line" p18a p20 "")             (setq e12 (entlast))
(command "line" p20 p21 "")              (setq e13 (entlast))
(command "extend" e9 "" p21 "")          (setq e14 (entlast))
;;
(setq ed14 (entget e14)
        el (nth 2 (assoc 10 ed14))        
        et (nth 2 (assoc 11 ed14))
        eh (- et el)
      ucpr (+ dor eh))
;;
(command "mirror" e12 e13 e10 "" p19 p12 "")
(command "line" p34 p35 "")              (setq e23 (entlast))      
(command "line" p35 p36 "")              (setq e24 (entlast))
(command "fillet" e23 e24)
(command "trim" e10 "" p36 ""
         "redraw")
(command "line" p38 p39 "")              (setq e15 (entlast))
(command "line" p40 p41 "")              (setq e16 (entlast)) 
(command "line" p8 p9 "")                (setq e17 (entlast))
(command "line" p42 p43 "")              (setq e18 (entlast))
(command "zoom" "p") 
(command "chprop" e15 e16 e17 e18 "" "la" "cen-m" ""
         "chprop" e1 e2 "" "la" "hid-r" "")
) ;progn
) ;end if -------Elevation
;;;;;;;;;;;;;;;;;;;;;;;;;;
(if (= an2 "f")    ; Front
(progn
(initget 1)
(setq po (getpoint "\nPick!  UCP center: " ))
(setq p1 (polar po (dtr 90.0) l1)
      p2 (polar po (dtr 0.0) l1)
      p3 (polar po (dtr 180.0) l1)
      p4 (polar p3 (dtr 270.0) (- h h1))
      p5 (polar po (dtr 270.0) (- h h1))
      p6 (polar p5 (dtr 180.0) (/ j 2.0))
      p7 (polar p5 (dtr 180.0) (/ l 2.0))
      p8 (polar p7 (dtr 270.0) h1)
      p9 (polar p8 (dtr 0.0) (+ c (/ (- l j) 2.0)))
     p10 (polar p9 (dtr 90.0) (/ h1 10.0))
     p11 (polar p9 (dtr 90.0) h1)
     p12 (polar p6 (dtr 0.0) (/ n2 2.0))
     p13 (polar p12 (dtr 270.0) h1)
     p14 (polar p6 (dtr 90.0) 3.0)
     p15 (polar p6 (dtr 270.0) (+ h1 3.0))   
     p16 (polar p1 (dtr 90.0) 5.0)
     p17 (polar p1 (dtr 270.0) (+ h2 5.0))
     p18 (polar p3 (dtr 180.0) 5.0) 
     p19 (polar p2 (dtr 0.0) 5.0)
     p20 (polar po (dtr 90.0) (/ bd 2.0))
     p21 (polar p20 (dtr 180.0) (/ m1 2.0))   
     p22 (polar p21 (dtr 0.0) of) 
     p23 (polar p22 (dtr 270.0) 3.0)
     p24 (polar p21 (dtr 270.0) 3.0)
     p25 (polar p10 (dtr 0.0) (- j (* c 2.0)))   
     p26 (polar po (dtr 330.0) (- (/ d 2.0) 2.5))
     p27 (polar po (dtr 330.0) (+ (/ bd 2.0) 2.5)))
;;;;;;;;     
(command "line" p11 p7 "")              (setq e1 (entlast))
(command "line" p7 p8 "")               (setq e2 (entlast)) 
(command "line" p8 p9 "")               (setq e3 (entlast)) 
(command "line" p9 p11 "")              (setq e4 (entlast)) 
(command "line" p12 p13 "")             (setq e5 (entlast)) 
(command "mirror" e5 "" p6 p15 "")      (setq e6 (entlast))
(command "fillet" "r" (+ r 2))
(command "fillet" e1 e2)                (setq e7 (entlast))
(command "fillet" e4 e1)                (setq e8 (entlast))
(command "line" p14 p15 "")             (setq e8a (entlast)) 
(command "chprop" e8a "" "la" "cen-m" "")
(command "line" p3 p4 "")               (setq e9 (entlast)) 
(command "chprop" e5 e6 "" "la" "hid-r" "")
(command "mirror" e1 e2 e3 e4 e5 e6 e7 e8 e8a e9 "" po p5 "")
(command "line" p22 p23 "")             (setq e12 (entlast))
(command "line" p21 p24 "")             (setq e13 (entlast))
(command "circle" po "d" d)             (setq e10 (entlast))
(command "circle" po "d" bd)            (setq e11 (entlast))
(command "extend" e10 "" "f" p24 p23 "" ""        
         "trim" e11 "" "f" p22 p21 "" ""   
         "chprop" e12 e13 "" "la" "hid-r" "")
(command "mirror" e12 "" p20 po "")     (setq e13a (entlast))
(command "mirror" e13 "" p20 po "")     (setq e13b (entlast))
(command "array" e12 e13 e13a e13b "" "p" po 3 "" "" 
         "erase" e12 e13 e13a e13b "")
(command "redraw")
(command "line" p26 p27 "")             (setq e13c (entlast))
(command "mirror" e13c "" p20 po "")    (setq e13d (entlast))
(command "arc" p2 p1 p3
         "line" p10 p25 ""
         "circle" po (+ tt (/ bd 2.0))
         "circle" po h3
         "circle" po dor)
(if (> ucpr 1)
(command "circle" po ucpr)
(setq ucpr 0)
)
(command "line" p16 p17 "")             (setq e14 (entlast)) 
(command "line" p18 p19 "")             (setq e15 (entlast)) 
(command "chprop" e14 e15 e13c e13d "" "la" "cen-m" "") 
) ;progn
) ;end if -------Front
;;;;;;;;;;;;;;;;;;;;;;;;;;
(if (= an2 "t")    ; Top
(progn
(initget 1)
(setq p1 (getpoint "\nPick!  UCP top center: " ))
(setq p2 (polar p1 (dtr 270.0) m)
      p3 (polar p2 (dtr 270.0) wh1)
      p4 (polar p2 (dtr 90.0) wh1)
      p5 (polar p1 (dtr 180.0) (/ bd 2.0))
      p6 (polar p1 (dtr 180.0) (/ d 2.0))
      p7 (polar p6 (dtr 0.0) d)
      p8 (polar p5 (dtr 0.0) bd)
      p9 (polar p8 (dtr 270.0) (+ m n))
     p10 (polar p9 (dtr 180.0) bd)
     p11 (polar p10 (dtr 0.0) tt)
     p12 (polar p11 (dtr 0.0) d)
     p13 (polar p12 (dtr 90.0) n)
     p14 (polar p13 (dtr 180.0) d)
     p15 (polar p14 (dtr 180.0) tt)
     p16 (polar p15 (dtr 0.0) bd)
     p17 (polar p2 (dtr 270.0) (- n g))
     p18 (polar p2 (dtr 180.0) l1)
     p19 (polar p2 (dtr 180.0) (/ j 2.0))
     p20 (polar p2 (dtr 180.0) (/ l 2.0))
     p21 (polar p20 (dtr 90.0) (/ a 2.0))
     p22 (polar p18 (dtr 90.0) (/ a 2.0))
     p23 (polar p21 (dtr 0.0) (+ (/ (- l j) 2.0) c))
     p24 (polar p23 (dtr 270.0) a)
     p25 (polar p22 (dtr 270.0) a)
     p26 (polar p21 (dtr 270.0) a)
     p27 (polar p19 (dtr 180.0) (/ sh 2.0))
     p28 (polar p27 (dtr 90.0) (/ n1 2.0))
     p29 (polar p28 (dtr 0.0) sh)
     p30 (polar p28 (dtr 270.0) n1)
     p31 (polar p19 (dtr 90.0) (+ (/ n1 2.0) 3.0))
     p32 (polar p31 (dtr 270.0) (+ n1 6.0))
     p33 (polar p19 (dtr 0.0) c)
     p34 (polar p1 (dtr 90.0) 5.0)
     p35 (polar p2 (dtr 270.0) (+ n 5.0))
     p36 (polar p20 (dtr 180.0) 5.0)
     p37 (polar p36 (dtr 0.0) (+ l 10.0))
     p38 (polar p22 (dtr 0.0) (* l1 2.0))
     p39 (polar p38 (dtr 270.0) a)
     p40 (polar p33 (dtr 0.0) (- j (* c 2.0)))
     p41 (polar p17 (dtr 180.0) (+ (/ m1 2.0) 2.0))
     p42 (polar p41 (dtr 0.0) (+ m1 4.0))
     p43 (polar p22 (dtr 270.0) (* r 1.6))
     p44 (polar p25 (dtr 90.0) (* r 1.6))
     p45 (polar p38 (dtr 270.0) (* r 1.6))
     p46 (polar p39 (dtr 90.0) (* r 1.6)))
;;;;;;;;;
(command "zoom" p22 p39)
(command "arc" p43 p4 p45)              (setq e1 (entlast))
(command "arc" p46 p3 p44)              (setq e2 (entlast))
(command "line" p8 p9 "")               (setq e3 (entlast))
(command "line" p5 p10 "")              (setq e4 (entlast))
(command "line" p7 p12 "")              (setq e5 (entlast))
(command "line" p6 p11 "")              (setq e6 (entlast))
(command "line" p5 p8 ""             
         "line" p10 p9 "")              
(command "trim" e1 e2 "" p16 p15 "")      
(command "trim" e1 e2 "" p13 "")        (setq e6a (entlast)) 
(command "trim" e1 e2 "" p14 "")        (setq e6b (entlast)) 
(command "line" p43 p44 ""             
         "line" p45 p46 "")              
(command "line" p23 p21 "")             (setq e7 (entlast))
(command "line" p21 p26 "")             (setq e8 (entlast))
(command "line" p26 p24 "")             (setq e9 (entlast))
(command "line" p24 p23 "")             (setq e10 (entlast))
(command "fillet" "r" (+ r 1.0))
(command "fillet" e7 e8)                (setq e11 (entlast))
(command "fillet" e8 e9)                (setq e12 (entlast))
(command "fillet" e9 e10)               (setq e13 (entlast))
(command "fillet" e10 e7)               (setq e14 (entlast))
(command "arc" p28 "c" p27 p30)         (setq e15 (entlast)) 
(command "mirror" e15 "" p31 p19 "")    (setq e16 (entlast))
(command "line" p28 p29 "")             (setq e17 (entlast))
(command "mirror" e17 "" p20 p19 "")    (setq e18 (entlast))
(command "line" p31 p32 "")             (setq e19 (entlast))
(command "chprop" e19 "" "la" "cen-m" "")
(command "mirror" e7 e8 e9 e10 e11 e12 e13 e14 e15 e16 e17 e18 e19 "" p1 p2 "") 
(command "trim" e1 e2 "" p33 p40 "")
(command "line" p34 p35 "")             (setq e20 (entlast))
(command "line" p36 p37 "")             (setq e21 (entlast))
(command "line" p41 p42 "")             (setq e22 (entlast))
(command "chprop" e20 e21 e22 "" "la" "cen-m" "")
(command "chprop" e5 e6 e6a e6b "" "la" "hid-r" "")
(command "circle" p17 "d" m1)
(command "circle" p17 "d" gd)
(command "zoom" "p")
) ;progn
) ;end if -------Top
(princ (strcat "\nYou select:  <UCP" nd ">"  
                                   "   shaft dia(mm)=" (rtos d)
                                   "   setbolt=M" (rtos m2)  
                                   "   weight(kg)=" (rtos w) ))
)
);end if-ucp brg.  
;-----------------------------------------------------------------------------------
(if (= ans 5)
 (progn     
(textpage)
(princ "\n  No  dxD   Length              No   dxD    Length               ") 
(princ "\n===================================================================") 
(princ "\n [1]  3x5 - 3,4,5,6            [21] 26x30 - 15,20,25,30          ")
(princ "\n [2]  4x6 - 4,6,8              [22] 28x32 - 12,15,20,25,30,35,40 ")
(princ "\n [3]  5x7 - 4,5,6,8            [23] 30x34 - 12,15,25,40          ")
(princ "\n [4]  6x8 - 5,6,7,8,10         [24] 31x35 - 15,20,25,30,40       ")
(princ "\n [5]  7x9 - 5,7,10,12          [25] 32x36 - 20,25,30,35,40,50    ")  
(princ "\n [6]  8x10- 5,6,7,8,10,12      [26] 35x39 - 12,25,30,35,40       ")
(princ "\n [7]  9x11- 10,20              [27] 38x42 - 20,25,30,35,40,50    ")  
(princ "\n [8] 10x12- 6,7,8,10,12        [28] 40x44 - 12,15,20,25,30,35,40,50")
(princ "\n [9] 12x14- 6,8,10,12,15       [29] 45x50 - 20,25,30,35,40,50,60 ")
(princ "\n[10] 13x15- 8,10,15,20         [30] 50x55 - 25,30,35,40,50,60    ")  
(princ "\n[11] 14x16- 10,12,16,20,25     [31] 55x60 - 30,35,40,60          ")
(princ "\n[12] 15x17- 8,10,12,15,20,25   [32] 60x65 - 30,40,50,60          ")
(princ "\n[13] 16x18- 10,12,15           [33] 65x70 - 30,35,40,50,60,80    ")
(princ "\n[14] 17x19- 15,20,25           [34] 70x75 - 30,35,40,50,60,80    ")
(princ "\n[15] 18x20- 10,12,15           [35] 75x80 - 40,50,60,80          ")  
(princ "\n[16] 19x22- 10,15,20,25,30     [36] 80x85 - 40,50,60,80          ")
(princ "\n[17] 20x23- 10,12,15,20,25     [37] 85x90 - 40,50,60,80          ")
(princ "\n[18] 22x25- 10,12,15,20,25,30  [38] 90x95 - 40,60,90             ")
(princ "\n[19] 24x27- 15,20,25,30,35     [39] 100x105- 50,70,95            ")
(princ "\n[20] 25x28- 10,12,15,20,30     [40] 110x115- 50,70,95            ")
(princ "\n===================================================================")
(initget 7)
(setq an1 (getint "\nSelect No. ? : " ))
(initget 7)
(setq l (getreal "\nLength ? : " ))
(graphscr)
(cond
((= an1 1) (setq size (list 3 5)))
((= an1 2) (setq size (list 4 6)))
((= an1 3) (setq size (list 5 7)))
((= an1 4) (setq size (list 6 8)))
((= an1 5) (setq size (list 7 9)))
((= an1 6) (setq size (list 8 10)))
((= an1 7) (setq size (list 9 11)))
((= an1 8) (setq size (list 10 12)))
((= an1 9) (setq size (list 12 14)))
((= an1 10) (setq size (list 13 15)))
((= an1 11) (setq size (list 14 16)))
((= an1 12) (setq size (list 15 17)))
((= an1 13) (setq size (list 16 18)))
((= an1 14) (setq size (list 17 19)))
((= an1 15) (setq size (list 18 20)))
((= an1 16) (setq size (list 19 22)))
((= an1 17) (setq size (list 20 23)))
((= an1 18) (setq size (list 22 25)))
((= an1 19) (setq size (list 24 27)))
((= an1 20) (setq size (list 25 28)))
((= an1 21) (setq size (list 26 30)))
((= an1 22) (setq size (list 28 32)))
((= an1 23) (setq size (list 30 34)))
((= an1 24) (setq size (list 31 35)))
((= an1 25) (setq size (list 32 36)))
((= an1 26) (setq size (list 35 39)))
((= an1 27) (setq size (list 38 42)))
((= an1 28) (setq size (list 40 44)))
((= an1 29) (setq size (list 45 50)))
((= an1 30) (setq size (list 50 55)))
((= an1 31) (setq size (list 55 60)))
((= an1 32) (setq size (list 60 65)))
((= an1 33) (setq size (list 65 70)))
((= an1 34) (setq size (list 70 75)))
((= an1 35) (setq size (list 75 80)))
((= an1 36) (setq size (list 80 85)))
((= an1 37) (setq size (list 85 90)))
((= an1 38) (setq size (list 90 95)))
((= an1 39) (setq size (list 100 105)))
((= an1 40) (setq size (list 110 115)))
) 
(setq d (nth 0 size)        ;ID
      o (nth 1 size)        ;OD
      thk (/ (- o d) 2.0))      ;thk
(cond
((= thk 1.0) (setq c 0.3))
((= thk 1.5) (setq c 0.8))
((or (= thk 2.0) (= thk 2.5)) (setq c 1.0))
)
(setq c1 (/ c (cos (dtr 20)))     ;od chamfer length
      c2 (/ 0.5 (cos (dtr 45))))  ;id chamfer length 
(setq pt (getpoint "\nPick bush left center : " ))
(setq p1 (polar pt (dtr 90) (+ (/ d 2.0) 0.5))
      p2 (polar p1 (dtr 0) l)  
      p3 (polar p2 (dtr 90) (- thk 0.5)) 
      p4 (polar p3 (dtr 180) l) 
      p5 (polar p3 (dtr 180) c) 
      p6 (polar p5 (dtr -20) c1) 
      p7 (polar p6 (dtr 180) l) 
      p8 (polar p4 (dtr 0) c) 
      p9 (polar p1 (dtr -45) c2)   
     p10 (polar p2 (dtr 225) c2)
     p11 (polar pt (dtr 270) (+ 0.5 (/ d 2.0)))
     p12 (polar p11 (dtr 0) l)
     p13 (polar pt (dtr 0) thk))
(command "pline" p1 p9 p10 p2 p6 p5 p8 p7 p1 "") (setq ep1 (entlast))    
(command "mirror" ep1 "" pt p13 "") (setq p14 (entlast))  
(command "pline" p1 p11 "")         (setq p15 (entlast))  
(command "pline" p2 p12 "")         (setq p16 (entlast))
(command "rotate" ep1 p14 p15 p16 "" pt "\\")  
(princ (strcat "\nYou select: " (rtos d) "x" (rtos o) "x" (rtos l) "L" ))
)
);end if-du bush
;-----------------------------------------------------------------------------------
 (command "undo" "e")  
 (setvar "cmdecho" ocmde)
 (setvar "osmode" oosmo)
 (setvar "peditaccept" oed) 
 (setq *error* olderr) 
 (princ)
);defun
;;;;;;;;;;
(princ "\n\tBEARING [typing BRG]: 1999.7/by K.W.PARK")
(princ)
