(defun c:ds ()
(setvar "cmdecho" 0)
(setq ent (ssget '((0 . "LINE,CIRCLE,ARC,POLYLINE,LWPOLYLINE,ELLIPSE,SPLINE"))))
(setq n 0 dis 0)
(repeat (sslength ent)
(setq ent_l (ssname ent n))
(command "lengthen" ent_l "")
(setq dis (+ dis (GETVAR "PERIMETER")))
(setq n (1+ n))
)
(setq dis (rtos (/ dis 1000) 2 2))
(prompt (strcat "\n>> 선택 객체수 = "(rtos n)"   길이합계 = " dis))(princ)
(princ "\nDo You Want Write it into the DWG? <y> ")
    (setq z (strcase (getstring)))
    (if (or (= z "") (= z "Y"))
        (progn
            (setq pt (getpoint "\nText Point: "))
            (setq h (getvar "textsize"))
            (prompt "\nText Height: ")
            (princ H)
            (princ "  : ")
            (setq z (getdist))
            (if z
                (setq h z)
            )
			(entmake
				(list
					(cons 0 "TEXT")
					(cons 10 pt)
					(cons 40 h)
					(cons 1 dis)
				)
			)
          	;|
            (command "text"
                     (setq z pt)
                     (setq z h)
                     (setq z 0.0)
                     (setq z dis)
            )
			|;
			(setvar "cmdecho" 1)
        )
    )
)
