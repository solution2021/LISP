; 면적 & 냉방지수 & 감지기 계산 프로그램 BY HOYA (Seo Ju-Ho)
;
;                                      Date : 2006.06.30

(defun c:pyo ()
(setvar "cmdecho" 0)
 (PROMPT "\n ### 전기&소방 도움프로그램 By HOYA ### \n 원하는 영역을 그리시오.")
      (setq old_osnap (getvar "osmode"))
     (command "-layer" "m" "230" "c" "230" "" "")
     (setq pt (getpoint))
     (command "_pline" pt)
     (setq pau (getvar "cmdnames"))
     (while (= pau (getvar "cmdnames"))
     (command pause)     
     )
     (command "-layer" "off" "*" "n" "")
     (setq old_osnap (getvar "osmode"))
      (setq sc (getvar "ltscale"))
     (setq ds (* sc 1.5))
     (setq pt1 (getpoint "\n면적산출할 점을 찍으시오 ->"))
     (setq pt2 (list (car pt1) (- (cadr pt1) ds)))
     (setq pt3 (list (car pt2) (- (cadr pt2) ds)))
     (command "bpoly" pt1 "" ) 
     (command "area" "e" "l")
     (command "ERASE" "l" "")
     (setq ar (getvar "area"))
     (setq ar1 (/ ar 1000000))
     (setq pyung (/ (/ ar 1000000) 3.3058))
     (setq rt1 (/ (* ar 0.00015) 2500))
     (setq d1 (/ (/ ar 1000000) 70))
     (setq d2 (/ (/ ar 1000000) 60))
     (setq d3 (/ (/ ar 1000000) 150))
     (setq d4 (/ (/ ar 1000000) 35))
     (setq d5 (/ (/ ar 1000000) 30))
     (setq d6 (/ (/ ar 1000000) 75))
     (setq d6 (rtos (+ d6 0.49) 2 0))
     (setq d5 (rtos (+ d5 0.49) 2 0))
     (setq d4 (rtos (+ d4 0.49) 2 0))
     (setq d3 (rtos (+ d3 0.49) 2 0))
     (setq d2 (rtos (+ d2 0.49) 2 0))
     (setq d1 (rtos (+ d1 0.49) 2 0))
      (setq rt3 (rtos rt1 2 1))
     (setq rt2 (ATOI rt3))
     (cond ((<= rt2 3) (setq rt "3 RT"))
           ((<= rt2 5) (setq rt "5 RT"))
           ((<= rt2 7.5) (setq rt "7.5 RT"))
           ((<= rt2 10) (setq rt "10 RT"))
           ((<= rt2 15) (setq rt "15 RT"))
           )
     (setq pyung (rtos pyung 2 2))
     (setq ar1 (rtos ar1 2 2))
     (setq disp1 (strcat "면적: "ar1" M2 ( "pyung" 평) / 냉방지수 "rt" " ))
     (setq disp2 (strcat "감지기4m미만: 차동식 "d1" 개 / 정온식 "d2" 개 /  연기식 "d3" 개" ))
     (setq disp3 (strcat "감지기4m이상: 차동식 "d4" 개 / 정온식 "d5" 개 /  연기식 "d6" 개" ))
     (command "ERASE" "l" "")
     (setq z (strcase (getstring "\n도면에 출력(Y) / 화면에 표현(N) ? [N]")))
        (if (= z "Y")
           (progn
(prompt "\n결과를 나타낼 첫번째점을 지정:")
     (setq Z (getdist))
         (if Z
             (setq dsh Z)
)
  (cond ((= LSCALE 1) (COMMAND "TEXTSIZE" "2.5"))
        ((= LSCALE 30) (COMMAND "TEXTSIZE" "75"))
((= LSCALE 50) (COMMAND "TEXTSIZE" "125"))
((= LSCALE 60) (COMMAND "TEXTSIZE" "150"))
((= LSCALE 75) (COMMAND "TEXTSIZE" "187.5"))
((= LSCALE 100) (COMMAND "TEXTSIZE" "250"))
((= LSCALE 150) (COMMAND "TEXTSIZE" "375"))
((= LSCALE 200) (COMMAND "TEXTSIZE" "500"))
((= LSCALE 250) (COMMAND "TEXTSIZE" "625"))
((= LSCALE 300) (COMMAND "TEXTSIZE" "750"))
((= LSCALE 400) (COMMAND "TEXTSIZE" "1000"))
((= LSCALE 600) (COMMAND "TEXTSIZE" "1500"))
           )    
     (setq dsh (getvar "textsize"))
              (COMMAND "TEXT" ;"s" "ghs"
              (SETQ Z PT1)
                  (SETQ Z dsh)
                  (SETQ Z 0.0)
                  (SETQ Z disp1)
                  )

         (COMMAND "TEXT"
                  (SETQ Z PT2)
                  (SETQ Z dsh)
                  (SETQ Z 0.0)
                  (SETQ Z disp2)
                  )
          (COMMAND "TEXT"
                  (SETQ Z PT3)
                  (SETQ Z dsh)
                  (SETQ Z 0.0)
                  (SETQ Z disp3)
                  )
)
 (progn
(alert (strcat "\n면 적 :   "ar1"［㎡] / "Pyung" 평［py]\n냉방지수 :  "rt" ("rt3" RT)\n\n┌────감지기4m미만────┐\n│         차동식(2종)     "d1" 개        │\n│         정온식(1종)     "d2" 개        │\n│         연기식(1종)     "d3" 개        │\n├────감지기4m이상────┤\n│         차동식(2종)     "d4" 개        │\n│         정온식(1종)     "d5" 개        │\n│         연기식(1종)     "d6" 개        │\n└──────────────┘ "))
)
)
  (if (tblsearch "layer" "4")
    (command "-layer" "s" "4" "")
    (command "-layer" "m" "4" "")
  )

(command "-layer" "on" "*" "")
(setvar "osmode" old_osnap)
(princ "\n *** 작업완료 ***")
(princ)
)
;**************************
