;**************************************************************************
;SPRING                                                                    
;2011/10/30                                               [By K.W.Park]    
;**************************************************************************
(defun spring_er (s)
(if (/= s "Function Cancelled")
(if	(= s "quit / exit abort / cancelled")
(princ)
(princ (strcat "\nERROR :" s))
)
)
(setvar "cmdecho" ocmde)
(setvar "osmode" osm)
(graphscr)
(setq *error* olderr)
(princ)
)
;-------------------------
(defun dtr (dtr1)
(* pi (/ dtr1 180.00))
)
(defun rtd (rtd1)
(/ (* 180.00 rtd1) pi)
)
;------------------------------------------------------------------
(defun DIESPRING-LIGHT ()
(princ
(strcat
"\n================================================================"
"\n                     CORE SPRING (LIGHT)              ISO"
"\n================================================================"
"\n   No.선택시 kg으로 환산 (1N/mm=0.102kg/mm / 1N=0.102kg)"
"\n----------------------------------------------------------------"
"\n   No.   O.D   I.D      H      RATE      MAX.        MAX."
"\n        (mm)   (mm)    (mm)   (N/mm)    LOAD(N)  DEFLECTION(mm)"
"\n <10x5>---------------------------------------------------------"
"\n   1.    10     5       25     10.0     103.0     10.3"
"\n   2.    10     5       32      8.5     111.4     13.1"
"\n   3.    10     5       38      6.8     106.1     15.6"
"\n   4.    10     5       44      6.0     108.0     18.0"
"\n   5.    10     5       51      5.0     104.5     20.9"
"\n   6.    10     5       64      4.3     111.8     26.0"
"\n   7.    10     5       76      3.2      99.8     31.2"
"\n   8.    10     5      305      1.1     137.5    125.0"
"\n <12.5x6.3>---------------------------------------------"
"\n   9.    12.5   6.3     25     17.9     184.4     10.3"
"\n  10.    12.5   6.3     32     16.4     214.8     13.1"
"\n  11.    12.5   6.3     38     13.6     212.2     15.6"
"\n  12.    12.5   6.3     44     12.1     217.8     18.0"
"\n  13.    12.5   6.3     51     11.4     238.3     20.9"
"\n  14.    12.5   6.3     64      9.3     244.6     26.3"
"\n  15.    12.5   6.3     76      7.1     221.5     31.2"
"\n  16.    12.5   6.3     89      5.4     197.1     36.5"
"\n  17.    12.5   6.3    305      1.4     175.0    125.0"
"\n <16x8>-------------------------------------------------"
"\n  18.    16     8       25     23.4     241.0     10.3"
"\n  19.    16     8       32     22.9     300.0     13.1"
"\n  20.    16     8       38     19.3     301.1     15.6"
"\n  21.    16     8       44     17.1     307.8     18.0"
"\n  22.    16     8       51     15.7     328.1     20.9"
"\n  23.    16     8       64     10.7     281.4     26.3"
"\n  24.    16     8       76     10.0     312.0     31.2"
"\n  25.    16     8       89      8.6     313.9     36.5"
"\n  26.    16     8      102      7.8     326.0     41.8"
"\n  27.    16     8      305      2.5     312.5    125.0"     
"\n--------------------------------------------------------"
"\n LIGHT <MORE> -press any key- ^See the Top:"
);princ
);strca
(grread)
(princ
(strcat
"\n <20x10>------------------------------------------------"
"\n  28.    20    10       25     55.8     569.2     10.2"
"\n  29.    20    10       32     45.0     562.5     12.5"
"\n  30.    20    10       38     33.3     499.5     15.0"
"\n  31.    20    10       44     30.0     540.0     18.0"
"\n  32.    20    10       51     24.5     490.0     20.0"
"\n  33.    20    10       64     20.0     500.0     25.0"
"\n  34.    20    10       76     16.0     480.0     30.0"
"\n  35.    20    10       89     14.0     490.0     35.0"
"\n  36.    20    10      102     12.0     492.0     41.0"
"\n  37.    20    10      115     10.9     501.4     46.0"
"\n  38.    20    10      127      9.5     484.5     51.0"
"\n  39.    20    10      139      8.4     470.4     56.0"
"\n  40.    20    10      152      7.5     457.5     61.0"
"\n  41.    20    10      305      4.0     488.0    122.0"  
"\n <25x12.5>----------------------------------------------"
"\n  42.    25    12.5     25    100.0    1020.2     10.2"
"\n  43.    25    12.5     32     80.3    1003.8     12.5"
"\n  44.    25    12.5     38     62.0     930.0     15.0"
"\n  45.    25    12.5     44     52.9     952.2     18.0"
"\n  46.    25    12.5     51     44.0     880.0     20.0"
"\n  47.    25    12.5     64     35.2     880.0     25.0"
"\n  48.    25    12.5     76     28.0     840.0     30.0"
"\n  49.    25    12.5     89     24.0     840.0     35.0"
"\n  50.    25    12.5    102     21.1     865.1     41.0"
"\n  51.    25    12.5    115     18.7     860.2     46.0"
"\n  52.    25    12.5    127     16.7     851.7     51.0"
"\n  53.    25    12.5    139     15.3     856.8     56.0"
"\n  54.    25    12.5    152     14.0     854.0     61.0"
"\n  55.    25    12.5    178     12.5     887.5     71.0"
"\n  56.    25    12.5    203     10.4     842.4     81.0"
"\n  57.    25    12.5    305      7.0     854.0    122.0"
"\n <32x16>------------------------------------------------"
"\n  58.    32    16       38     94.0    1410.0     15.0"
"\n  59.    32    16       44     79.5    1431.0     18.0"
"\n  60.    32    16       51     67.0    1340.0     20.0"
"\n  61.    32    16       64     53.0    1325.0     25.0"
"\n  62.    32    16       76     44.0    1320.0     30.0"
"\n  63.    32    16       89     37.2    1302.0     35.0"
"\n  64.    32    16      102     32.0    1312.0     41.0"
"\n  65.    32    16      115     29.0    1334.0     46.0"
"\n  66.    32    16      127     25.0    1275.0     51.0"
"\n  67.    32    16      139     23.0    1288.0     56.0"
"\n  68.    32    16      152     21.5    1311.5     61.0"
"\n  69.    32    16      178     18.2    1292.2     71.0"
"\n  70.    32    16      203     15.8    1279.8     81.0"
"\n  71.    32    16      254     12.5    1275.0    102.0"
"\n  72.    32    16      305     10.3    1256.6    122.0"
"\n--------------------------------------------------------"
"\n LIGHT <MORE> -press any key- ^See the Top:"
);princ
);strcat
(grread)
(princ
(strcat
"\n <40x20>------------------------------------------------"
"\n  73.    40    20       51     92.0    1840.0     20.0"
"\n  74.    40    20       64     73.0    1825.0     25.0"
"\n  75.    40    20       76     63.0    1890.0     30.0"
"\n  76.    40    20       89     51.0    1785.0     35.0"
"\n  77.    40    20      102     43.0    1763.0     41.0"
"\n  78.    40    20      115     39.6    1821.6     46.0"
"\n  79.    40    20      127     37.0    1887.0     51.0"
"\n  80.    40    20      139     32.0    1792.0     56.0"
"\n  81.    40    20      152     28.0    1708.0     61.0"
"\n  82.    40    20      178     25.2    1789.2     71.0"
"\n  83.    40    20      203     22.7    1838.7     81.0"
"\n  84.    40    20      254     17.0    1734.0    102.0"
"\n  85.    40    20      305     14.8    1805.6    122.0"  
"\n <50x25>------------------------------------------------"
"\n  86.    50    25       64    156.0    3900.0     25.0"
"\n  87.    50    25       76    125.0    3750.0     30.0"
"\n  88.    50    25       89    109.0    3815.0     35.0"
"\n  89.    50    25      102     94.0    3854.0     41.0"
"\n  90.    50    25      115     81.0    3726.0     46.0"
"\n  91.    50    25      127     71.0    3621.0     51.0"
"\n  92.    50    25      139     66.5    3724.0     56.0"
"\n  93.    50    25      152     60.0    3660.0     61.0"
"\n  94.    50    25      178     52.0    3692.0     71.0"
"\n  95.    50    25      203     44.0    3564.0     81.0"
"\n  96.    50    25      254     35.0    3570.0    102.0"
"\n  97.    50    25      305     28.5    3477.0    122.0"
"\n <63x38>------------------------------------------------"
"\n  98.    63    38       76    189.0    5670.0     30.0"
"\n  99.    63    38       89    158.0    5530.0     35.0"
"\n 100.    63    38      102    131.0    5371.0     41.0"
"\n 101.    63    38      115    116.0    5336.0     46.0"
"\n 102.    63    38      127    103.0    5253.0     51.0"
"\n 103.    63    38      152     84.3    5142.3     61.0"
"\n 104.    63    38      178     71.5    5076.5     71.0"
"\n 105.    63    38      203     61.7    4997.7     81.0"
"\n 106.    63    38      254     47.0    4794.0    102.0"
"\n 107.    63    38      305     38.2    4660.4    122.0"
"\n LIGHT <END> See the Top================================="
);princ
);strcat
(setq an1 (getint "\nSelect No.: "));MENU/light
(cond
((= an1 1) (setq size '(10 5 25 10.0 103.0 10.3)))
((= an1 2) (setq size '(10 5 32 8.5 111.4 13.1)))
((= an1 3) (setq size '(10 5 38 6.8 106.1 15.6)))
((= an1 4) (setq size '(10 5 44 6.0 108.0 18.0)))
((= an1 5) (setq size '(10 5 51 5.0 104.5 20.9)))
((= an1 6) (setq size '(10 5 64 4.3 111.8 26.0)))
((= an1 7) (setq size '(10 5 76 3.2 99.8 31.2)))
((= an1 8) (setq size '(10 5 305 1.1 137.5 125.0)))
			;
((= an1 9) (setq size '(12.5 6.3 25 17.9 184.4 10.3)))
((= an1 10) (setq size '(12.5 6.3 32 16.4 214.8 13.1)))
((= an1 11) (setq size '(12.5 6.3 38 13.6 212.2 15.6)))
((= an1 12) (setq size '(12.5 6.3 44 12.1 217.8 18.0)))
((= an1 13) (setq size '(12.5 6.3 51 11.4 238.3 20.9)))
((= an1 14) (setq size '(12.5 6.3 64 9.3 244.6 26.3)))
((= an1 15) (setq size '(12.5 6.3 76 7.1 221.5 31.2)))
((= an1 16) (setq size '(12.5 6.3 89 5.4 197.1 36.5)))
((= an1 17) (setq size '(12.5 6.3 305 1.4 175.0 125.0)))
			;
((= an1 18) (setq size '(16 8 25 23.4 241.0 10.3)))
((= an1 19) (setq size '(16 8 32 22.9 300.0 13.1)))
((= an1 20) (setq size '(16 8 38 19.3 301.1 15.6)))
((= an1 21) (setq size '(16 8 44 17.1 307.8 18.0)))
((= an1 22) (setq size '(16 8 51 15.7 328.1 20.9)))
((= an1 23) (setq size '(16 8 64 10.7 281.4 26.3)))
((= an1 24) (setq size '(16 8 76 10.0 312.0 31.2)))
((= an1 25) (setq size '(16 8 89 8.6 313.9 36.5)))
((= an1 26) (setq size '(16 8 102 7.8 326.0 41.8)))
((= an1 27) (setq size '(16 8 305 2.5 312.5 125.0)))
			;
((= an1 28) (setq size '(20 10 25 55.8 569.2 10.2)))
((= an1 29) (setq size '(20 10 32 45.0 562.5 12.5)))
((= an1 30) (setq size '(20 10 38 33.3 499.5 15.0)))
((= an1 31) (setq size '(20 10 44 30.0 540.0 18.0)))
((= an1 32) (setq size '(20 10 51 24.5 490.0 20.0)))
((= an1 33) (setq size '(20 10 64 20.0 500.0 25.0)))
((= an1 34) (setq size '(20 10 76 16.0 480.0 30.0)))
((= an1 35) (setq size '(20 10 89 14.0 490.0 35.0)))
((= an1 36) (setq size '(20 10 102 12.0 492.0 41.0)))
((= an1 37) (setq size '(20 10 115 10.9 501.4 46.0)))
((= an1 38) (setq size '(20 10 127 9.5 484.5 51.0)))
((= an1 39) (setq size '(20 10 139 8.4 470.4 56.0)))
((= an1 40) (setq size '(20 10 152 7.5 457.5 61.0)))
((= an1 41) (setq size '(20 10 305 4.0 488.0 122.0)))
			;
((= an1 42) (setq size '(25 12.5 25 100.0 1020.2 10.2)))
((= an1 43) (setq size '(25 12.5 32 80.3 1003.8 12.5)))
((= an1 44) (setq size '(25 12.5 38 62.0 930.0 15.0)))
((= an1 45) (setq size '(25 12.5 44 52.9 952.2 18.0)))
((= an1 46) (setq size '(25 12.5 51 44.0 880.0 20.0)))
((= an1 47) (setq size '(25 12.5 64 35.2 880.0 25.0)))
((= an1 48) (setq size '(25 12.5 76 28.0 840.0 30.0)))
((= an1 49) (setq size '(25 12.5 89 24.0 840.0 35.0)))
((= an1 50) (setq size '(25 12.5 102 21.1 865.1 41.0)))
((= an1 51) (setq size '(25 12.5 115 18.7 860.2 46.0)))
((= an1 52) (setq size '(25 12.5 127 16.7 851.7 51.0)))
((= an1 53) (setq size '(25 12.5 139 15.3 856.8 56.0)))
((= an1 54) (setq size '(25 12.5 152 14.0 854.0 61.0)))
((= an1 55) (setq size '(25 12.5 178 12.5 887.5 71.0)))
((= an1 56) (setq size '(25 12.5 203 10.4 842.4 81.0)))
((= an1 57) (setq size '(25 12.5 305 7.0 854.0 122.0)))
			;
((= an1 58) (setq size '(32 16 38 94.0 1410.0 15.0)))
((= an1 59) (setq size '(32 16 44 79.5 1431.0 18.0)))
((= an1 60) (setq size '(32 16 51 67.0 1340.0 20.0)))
((= an1 61) (setq size '(32 16 64 53.0 1325.0 25.0)))
((= an1 62) (setq size '(32 16 76 44.0 1320.0 30.0)))
((= an1 63) (setq size '(32 16 89 37.2 1302.0 35.0)))
((= an1 64) (setq size '(32 16 102 32.0 1312.0 41.0)))
((= an1 65) (setq size '(32 16 115 29.0 1334.0 46.0)))
((= an1 66) (setq size '(32 16 127 25.0 1275.0 51.0)))
((= an1 67) (setq size '(32 16 139 23.0 1288.0 56.0)))
((= an1 68) (setq size '(32 16 152 21.5 1311.5 61.0)))
((= an1 69) (setq size '(32 16 178 18.2 1292.2 71.0)))
((= an1 70) (setq size '(32 16 203 15.8 1279.8 81.0)))
((= an1 71) (setq size '(32 16 254 12.5 1275.0 102.0)))
((= an1 72) (setq size '(32 16 305 10.3 1256.6 122.0)))
			;
((= an1 73) (setq size '(40 20 51 92.0 1840.0 20.0)))
((= an1 74) (setq size '(40 20 64 73.0 1825.0 25.0)))
((= an1 75) (setq size '(40 20 76 63.0 1890.0 30.0)))
((= an1 76) (setq size '(40 20 89 51.0 1785.0 35.0)))
((= an1 77) (setq size '(40 20 102 43.0 1763.0 41.0)))
((= an1 78) (setq size '(40 20 115 39.6 1821.6 46.0)))
((= an1 79) (setq size '(40 20 127 37.0 1887.0 51.0)))
((= an1 80) (setq size '(40 20 139 32.0 1792.0 56.0)))
((= an1 81) (setq size '(40 20 152 28.0 1708.0 61.0)))
((= an1 82) (setq size '(40 20 178 25.2 1789.2 71.0)))
((= an1 83) (setq size '(40 20 203 22.7 1838.7 81.0)))
((= an1 84) (setq size '(40 20 254 17.0 1734.0 102.0)))
((= an1 85) (setq size '(40 20 305 14.8 1805.6 122.0)))
			;
((= an1 86) (setq size '(50 25 64 156.0 3900.0 25.0)))
((= an1 87) (setq size '(50 25 76 125.0 3750.0 30.0)))
((= an1 88) (setq size '(50 25 89 109.0 3815.0 35.0)))
((= an1 89) (setq size '(50 25 102 94.0 3854.0 41.0)))
((= an1 90) (setq size '(50 25 115 81.0 3726.0 46.0)))
((= an1 91) (setq size '(50 25 127 71.0 3621.0 51.0)))
((= an1 92) (setq size '(50 25 139 66.5 3724.0 56.0)))
((= an1 93) (setq size '(50 25 152 60.0 3660.0 61.0)))
((= an1 94) (setq size '(50 25 178 52.0 3692.0 71.0)))
((= an1 95) (setq size '(50 25 203 44.0 3564.0 81.0)))
((= an1 96) (setq size '(50 25 254 35.0 3570.0 102.0)))
((= an1 97) (setq size '(50 25 305 28.5 3477.0 122.0)))
			;
((= an1 98) (setq size '(63 38 76 189.0 5670.0 30.0)))
((= an1 99) (setq size '(63 38 89 158.0 5530.0 35.0)))
((= an1 100) (setq size '(63 38 102 131.0 5371.0 41.0)))
((= an1 101) (setq size '(63 38 115 116.0 5336.0 46.0)))
((= an1 102) (setq size '(63 38 127 103.0 5253.0 51.0)))
((= an1 103) (setq size '(63 38 152 84.3 5142.3 61.0)))
((= an1 104) (setq size '(63 38 178 71.5 5076.5 71.0)))
((= an1 105) (setq size '(63 38 203 61.7 4997.7 81.0)))
((= an1 106) (setq size '(63 38 254 47.0 4794.0 102.0)))
((= an1 107) (setq size '(63 38 305 38.2 4660.4 122.0)))
);cond/light
);defun/DIESPRING-LIGHT
;-----------------------------------------------------------------------
(defun DIESPRING-MEDIUM	()
(princ
(strcat
"\n================================================================"
"\n                    CORE SPRING (MEDIUM)             ISO "
"\n================================================================"
"\n   No.선택시 kg으로 환산  (1N/mm=0.102kg/mm / 1N=0.102kg)"
"\n----------------------------------------------------------------"
"\n   No.   O.D   I.D      H      RATE      MAX.        MAX."
"\n        (mm)   (mm)    (mm)   (N/mm)    LOAD(N)  DEFLECTION(mm)"
"\n <10x5>---------------------------------------------------------"
"\n   1     10     5       25     16.0     152.0        9.5"
"\n   2     10     5       32     13.0     158.6       12.2"
"\n   3     10     5       38     11.9     171.4       14.4"
"\n   4     10     5       44     10.3     172.0       16.7"
"\n   5     10     5       51      8.9     172.7       19.4"
"\n   6     10     5       64      7.5     182.3       24.3"
"\n   7     10     5       76      5.3     153.2       28.9"
"\n   8     10     5      305      1.6     185.6      116.0"
"\n <12.5x6.3>-----------------------------------------------"
"\n   9     12.5   6.3     25     30.0     285.0        9.5"
"\n  10     12.5   6.3     32     24.8     302.6       12.2"
"\n  11     12.5   6.3     38     21.4     308.2       14.4"
"\n  12     12.5   6.3     44     18.5     309.0       16.7"
"\n  13     12.5   6.3     51     15.5     300.7       19.4"
"\n  14     12.5   6.3     64     12.1     294.0       24.3"
"\n  15     12.5   6.3     76      9.4     294.8       28.9"
"\n  16     12.5   6.3     89      8.4     283.9       33.8"
"\n  17     12.5   6.3    305      2.1     243.6      116.0"
"\n <16x8>---------------------------------------------------"
"\n  18     16     8       25     49.4     469.3        9.5"
"\n  19     16     8       32     37.1     452.6       12.2"
"\n  20     16     8       38     33.9     488.2       14.4"
"\n  21     16     8       44     30.0     501.0       16.7"
"\n  22     16     8       51     26.4     512.2       19.4"
"\n  23     16     8       64     20.5     498.2       24.3"
"\n  24     16     8       76     17.8     514.4       28.9"
"\n  25     16     8       89     15.2     513.8       33.8"
"\n  26     16     8      102     13.5     523.8       38.8"
"\n  27     16     8      305      4.8     556.8      116.0"
"\n----------------------------------------------------------"
"\n MEDIUM <MORE> -press any key- ^See the Top:"
);princ
);strcat
(grread)
(princ
(strcat
"\n <20x10>--------------------------------------------------"
"\n  28     20    10       25     98.0     921.2        9.4"
"\n  29     20    10       32     72.6     871.2       12.0"
"\n  30     20    10       38     56.0     784.0       14.0"
"\n  31     20    10       44     47.5     783.8       16.5"
"\n  32     20    10       51     41.7     792.3       19.0"
"\n  33     20    10       64     32.3     775.2       24.0"
"\n  34     20    10       76     25.1     702.8       28.0"
"\n  35     20    10       89     22.0     726.0       33.0"
"\n  36     20    10      102     19.8     752.4       38.0"
"\n  37     20    10      115     18.1     778.3       43.0"
"\n  38     20    10      127     16.6     796.8       48.0"
"\n  39     20    10      139     15.1     785.2       52.0"
"\n  40     20    10      152     13.2     752.4       57.0"
"\n  41     20    10      305      6.1     695.4      114.0"
"\n <25x12.5>------------------------------------------------"
"\n  42     25    12.5     25    147.0    1381.8        9.4"
"\n  43     25    12.5     32    118.0    1416.0       12.0"
"\n  44     25    12.5     38     93.0    1302.0       14.0"
"\n  45     25    12.5     44     80.8    1333.2       16.5"
"\n  46     25    12.5     51     68.6    1303.4       19.0"
"\n  47     25    12.5     64     53.0    1272.0       24.0"
"\n  48     25    12.5     76     43.2    1209.6       28.0"
"\n  49     25    12.5     89     38.2    1260.6       33.0"
"\n  50     25    12.5    102     33.0    1254.0       38.0"
"\n  51     25    12.5    115     28.0    1204.0       43.0"
"\n  52     25    12.5    127     25.9    1243.2       48.0"
"\n  53     25    12.5    139     23.2    1206.4       52.0"
"\n  54     25    12.5    152     20.8    1185.6       57.0"
"\n  55     25    12.5    178     17.8    1192.6       67.0"
"\n  56     25    12.5    203     15.8    1200.8       76.0"
"\n  57     25    12.5    305     10.2    1162.8      114.0"
"\n <32x16>--------------------------------------------------"
"\n  58     32    16       38    185.0    2590.0       14.0"
"\n  59     32    16       44    158.0    2607.0       16.5"
"\n  60     32    16       51    134.0    2546.0       19.0"
"\n  61     32    16       64     99.0    2376.0       24.0"
"\n  62     32    16       76     80.5    2254.0       28.0"
"\n  63     32    16       89     69.1    2280.3       33.0"
"\n  64     32    16      102     58.8    2234.4       38.0"
"\n  65     32    16      115     51.5    2214.5       43.0"
"\n  66     32    16      127     44.8    2150.4       48.0"
"\n  67     32    16      139     42.3    2199.6       52.0"
"\n  68     32    16      152     37.8    2154.6       57.0"
"\n  69     32    16      178     32.5    2177.5       67.0"
"\n  70     32    16      203     28.9    2196.4       76.0"
"\n  71     32    16      254     21.4    2033.0       95.0"
"\n  72     32    16      305     18.3    2086.2      114.0"
"\n----------------------------------------------------------"
"\n MEDIUM <MORE> -press any key- ^See the Top:"
);princ
);strcat
(grread)
(princ
(strcat
"\n <40x20>--------------------------------------------------"
"\n  73     40    20       51    181.6    3450.4       19.0"
"\n  74     40    20       64    140.0    3360.0       24.0"
"\n  75     40    20       76    108.0    3024.0       28.0"
"\n  76     40    20       89     90.7    2993.1       33.0"
"\n  77     40    20      102     81.0    3078.0       38.0"
"\n  78     40    20      115     71.8    3087.4       43.0"
"\n  79     40    20      127     62.7    3009.6       48.0"
"\n  80     40    20      139     57.5    2990.0       52.0"
"\n  81     40    20      152     51.6    2941.2       57.0"
"\n  82     40    20      178     44.1    2954.7       67.0"
"\n  83     40    20      203     36.7    2789.2       76.0"
"\n  84     40    20      254     30.1    2859.5       95.0"
"\n  85     40    20      305     24.6    2804.4      114.0"
"\n <50x25>--------------------------------------------------"
"\n  86     50    25       64    209.0    5016.0       24.0"
"\n  87     50    25       76    168.0    4704.0       28.0"
"\n  88     50    25       89    140.0    4620.0       33.0"
"\n  89     50    25      102    119.0    4522.0       38.0"
"\n  90     50    25      115    106.0    4558.0       43.0"
"\n  91     50    25      127     97.0    4656.0       48.0"
"\n  92     50    25      139     87.0    4524.0       52.0"
"\n  93     50    25      152     80.0    4560.0       57.0"
"\n  94     50    25      178     69.5    4656.5       67.0"
"\n  95     50    25      203     59.8    4544.8       76.0"
"\n  96     50    25      229     50.9    4377.4       86.0"
"\n  97     50    25      254     43.9    4170.5       95.0"
"\n  98     50    25      305     38.6    4400.4      114.0"
"\n <63x38>--------------------------------------------------"
"\n  99     63    38       76    312.0    8736.0       28.0"
"\n 100     63    38       89    260.0    8580.0       33.0"
"\n 101     63    38      102    221.0    8398.0       38.0"
"\n 102     63    38      115    187.0    8041.0       43.0"
"\n 103     63    38      127    168.0    8064.0       48.0"
"\n 104     63    38      152    136.0    7752.0       57.0"
"\n 105     63    38      178    114.0    7638.0       67.0"
"\n 106     63    38      203    100.0    7600.0       76.0"
"\n 107     63    38      229     89.2    7671.2       86.0"
"\n 108     63    38      254     78.4    7448.0       95.0"
"\n 109     63    38      305     64.7    7375.8      114.0"
"\n MEDIUM <END> See the Top================================="
);princ
);strcat
(setq an1 (getint "\nSelect No.: "))	;MENUt/medium 
(cond
((= an1 1) (setq size '(10 5 25 16.0 152.0 9.5)))
((= an1 2) (setq size '(10 5 32 13.0 158.6 12.2)))
((= an1 3) (setq size '(10 5 38 11.9 171.4 14.4)))
((= an1 4) (setq size '(10 5 44 10.3 172.0 16.7)))
((= an1 5) (setq size '(10 5 51 8.9 172.7 19.4)))
((= an1 6) (setq size '(10 5 64 7.5 182.3 24.3)))
((= an1 7) (setq size '(10 5 76 5.3 153.2 28.9)))
((= an1 8) (setq size '(10 5 305 1.6 185.6 116.0)))
				;
((= an1 9) (setq size '(12.5 6.3 25 30.0 285.0 9.5)))
((= an1 10) (setq size '(12.5 6.3 32 24.8 302.6 12.2)))
((= an1 11) (setq size '(12.5 6.3 38 21.4 308.2 14.4)))
((= an1 12) (setq size '(12.5 6.3 44 18.5 309.0 16.7)))
((= an1 13) (setq size '(12.5 6.3 51 15.5 300.7 19.4)))
((= an1 14) (setq size '(12.5 6.3 64 12.1 294.0 24.3)))
((= an1 15) (setq size '(12.5 6.3 76 9.4 294.8 28.9)))
((= an1 16) (setq size '(12.5 6.3 89 8.4 283.9 33.8)))
((= an1 17) (setq size '(12.5 6.3 305 2.1 243.6 116.0)))
				;
((= an1 18) (setq size '(16 8 25 49.4 469.3 9.5)))
((= an1 19) (setq size '(16 8 32 37.1 452.6 12.2)))
((= an1 20) (setq size '(16 8 38 33.9 488.2 14.4)))
((= an1 21) (setq size '(16 8 44 30.0 501.0 16.7)))
((= an1 22) (setq size '(16 8 51 26.4 512.2 19.4)))
((= an1 23) (setq size '(16 8 64 20.5 498.2 24.3)))
((= an1 24) (setq size '(16 8 76 17.8 514.4 28.9)))
((= an1 25) (setq size '(16 8 89 15.2 513.8 33.8)))
((= an1 26) (setq size '(16 8 102 13.5 523.8 38.8)))
((= an1 27) (setq size '(16 8 305 4.8 556.8 116.0)))
				;
((= an1 28) (setq size '(20 10 25 98.0 921.2 9.4)))
((= an1 29) (setq size '(20 10 32 72.6 871.2 12.0)))
((= an1 30) (setq size '(20 10 38 56.0 784.0 14.0)))
((= an1 31) (setq size '(20 10 44 47.5 783.8 16.5)))
((= an1 32) (setq size '(20 10 51 41.7 792.3 19.0)))
((= an1 33) (setq size '(20 10 64 32.3 775.2 24.0)))
((= an1 34) (setq size '(20 10 76 25.1 702.8 28.0)))
((= an1 35) (setq size '(20 10 89 22.0 726.0 33.0)))
((= an1 36) (setq size '(20 10 102 19.8 752.4 38.0)))
((= an1 37) (setq size '(20 10 115 18.1 778.3 43.0)))
((= an1 38) (setq size '(20 10 127 16.6 796.8 48.0)))
((= an1 39) (setq size '(20 10 139 15.1 785.2 52.0)))
((= an1 40) (setq size '(20 10 152 13.2 752.4 57.0)))
((= an1 41) (setq size '(20 10 305 6.1 695.4 114.0)))
				;
((= an1 42) (setq size '(25 12.5 25 147.0 1381.8 9.4)))
((= an1 43) (setq size '(25 12.5 32 118.0 1416.0 12.0)))
((= an1 44) (setq size '(25 12.5 38 93.0 1302.0 14.0)))
((= an1 45) (setq size '(25 12.5 44 80.8 1333.2 16.5)))
((= an1 46) (setq size '(25 12.5 51 68.6 1303.4 19.0)))
((= an1 47) (setq size '(25 12.5 64 53.0 1272.0 24.0)))
((= an1 48) (setq size '(25 12.5 76 43.2 1209.6 28.0)))
((= an1 49) (setq size '(25 12.5 89 38.2 1260.6 33.0)))
((= an1 50) (setq size '(25 12.5 102 33.0 1254.0 38.0)))
((= an1 51) (setq size '(25 12.5 115 28.0 1204.0 43.0)))
((= an1 52) (setq size '(25 12.5 127 25.9 1243.2 48.0)))
((= an1 53) (setq size '(25 12.5 139 23.2 1206.4 52.0)))
((= an1 54) (setq size '(25 12.5 152 20.8 1185.6 57.0)))
((= an1 55) (setq size '(25 12.5 178 17.8 1192.6 67.0)))
((= an1 56) (setq size '(25 12.5 203 15.8 1200.8 76.0)))
((= an1 57) (setq size '(25 12.5 305 10.2 1162.8 114.0)))
				;
((= an1 58) (setq size '(32 16 38 185.0 2590.0 14.0)))
((= an1 59) (setq size '(32 16 44 158.0 2607.0 16.5)))
((= an1 60) (setq size '(32 16 51 134.0 2546.0 19.0)))
((= an1 61) (setq size '(32 16 64 99.0 2376.0 24.0)))
((= an1 62) (setq size '(32 16 76 80.5 2254.0 28.0)))
((= an1 63) (setq size '(32 16 89 69.1 2280.3 33.0)))
((= an1 64) (setq size '(32 16 102 58.8 2234.4 38.0)))
((= an1 65) (setq size '(32 16 115 51.5 2214.5 43.0)))
((= an1 66) (setq size '(32 16 127 44.8 2150.4 48.0)))
((= an1 67) (setq size '(32 16 139 42.3 2199.6 52.0)))
((= an1 68) (setq size '(32 16 152 37.8 2154.6 57.0)))
((= an1 69) (setq size '(32 16 178 32.5 2177.5 67.0)))
((= an1 70) (setq size '(32 16 203 28.9 2196.4 76.0)))
((= an1 71) (setq size '(32 16 254 21.4 2033.0 95.0)))
((= an1 72) (setq size '(32 16 305 18.3 2086.2 114.0)))
				;
((= an1 73) (setq size '(40 20 51 181.6 3450.4 19.0)))
((= an1 74) (setq size '(40 20 64 140.0 3360.0 24.0)))
((= an1 75) (setq size '(40 20 76 108.0 3024.0 28.0)))
((= an1 76) (setq size '(40 20 89 90.7 2993.1 33.0)))
((= an1 77) (setq size '(40 20 102 81.0 3078.0 38.0)))
((= an1 78) (setq size '(40 20 115 71.8 3087.4 43.0)))
((= an1 79) (setq size '(40 20 127 62.7 3009.6 48.0)))
((= an1 80) (setq size '(40 20 139 57.5 2990.0 52.0)))
((= an1 81) (setq size '(40 20 152 51.6 2941.2 57.0)))
((= an1 82) (setq size '(40 20 178 44.1 2954.7 67.0)))
((= an1 83) (setq size '(40 20 203 36.7 2789.2 76.0)))
((= an1 84) (setq size '(40 20 254 30.1 2859.5 95.0)))
((= an1 85) (setq size '(40 20 305 24.6 2804.4 114.0)))
				;
((= an1 86) (setq size '(50 25 64 209.0 5016.0 24.0)))
((= an1 87) (setq size '(50 25 76 168.0 4704.0 28.0)))
((= an1 88) (setq size '(50 25 89 140.0 4620.0 33.0)))
((= an1 89) (setq size '(50 25 102 119.0 4522.0 38.0)))
((= an1 90) (setq size '(50 25 115 106.0 4558.0 43.0)))
((= an1 91) (setq size '(50 25 127 97.0 4656.0 48.0)))
((= an1 92) (setq size '(50 25 139 87.0 4524.0 52.0)))
((= an1 93) (setq size '(50 25 152 80.0 4560.0 57.0)))
((= an1 94) (setq size '(50 25 178 69.5 4656.5 67.0)))
((= an1 95) (setq size '(50 25 203 59.8 4544.8 76.0)))
((= an1 96) (setq size '(50 25 229 50.9 4377.4 86.0)))
((= an1 97) (setq size '(50 25 254 43.9 4170.5 95.0)))
((= an1 98) (setq size '(50 25 305 38.6 4400.4 114.0)))
				;
((= an1 99) (setq size '(63 38 76 312.0 8736.0 28.0)))
((= an1 100) (setq size '(63 38 89 260.0 8580.0 33.0)))
((= an1 101) (setq size '(63 38 102 221.0 8398.0 38.0)))
((= an1 102) (setq size '(63 38 115 187.0 8041.0 43.0)))
((= an1 103) (setq size '(63 38 127 168.0 8064.0 48.0)))
((= an1 104) (setq size '(63 38 152 136.0 7752.0 57.0)))
((= an1 105) (setq size '(63 38 178 114.0 7638.0 67.0)))
((= an1 106) (setq size '(63 38 203 100.0 7600.0 76.0)))
((= an1 107) (setq size '(63 38 229 89.2 7671.2 86.0)))
((= an1 108) (setq size '(63 38 254 78.4 7448.0 95.0)))
((= an1 109) (setq size '(63 38 305 64.7 7375.8 114.0)))
);cond
);defun/DIESPRING-MEDIUM
;------------------------------------------------------------------------
(defun DIESPRING-HEAVY ()
(princ
(strcat
"\n================================================================"
"\n                    CORE SPRING (HEAVY)              ISO"
"\n================================================================"
"\n   No.선택시 kg으로 환산 (1N/mm=0.102kg/mm / 1N=0.102kg)"
"\n----------------------------------------------------------------"
"\n   No.   O.D   I.D      H      RATE      MAX.        MAX."
"\n        (mm)   (mm)    (mm)   (N/mm)    LOAD(N)  DEFLECTION(mm)"
"\n <10x5>---------------------------------------------------------"
"\n   1     10     5       25     22.1     165.8        7.5"
"\n   2     10     5       32     17.5     168.0        9.6"
"\n   3     10     5       38     17.1     194.9       11.4"
"\n   4     10     5       44     15.0     198.0       13.2"
"\n   5     10     5       51     12.8     195.8       15.3"
"\n   6     10     5       64     10.7     205.4       19.2"
"\n   7     10     5       76      7.5     171.0       22.8"
"\n   8     10     5      305      2.1     192.2       91.5"
"\n <12.5x6.3>-----------------------------------------------"
"\n   9     12.5   6.3     25     42.1     315.8        7.5"
"\n  10     12.5   6.3     32     33.2     318.7        9.6"
"\n  11     12.5   6.3     38     29.3     334.0       11.4"
"\n  12     12.5   6.3     44     24.6     324.7       13.2"
"\n  13     12.5   6.3     51     19.6     299.9       15.3"
"\n  14     12.5   6.3     64     15.0     288.0       19.2"
"\n  15     12.5   6.3     76     13.2     301.0       22.8"
"\n  16     12.5   6.3     89     11.4     304.4       26.7"
"\n  17     12.5   6.3    305      2.8     256.2       91.5"
"\n <16x8>---------------------------------------------------"
"\n  18     16     8       25     75.7     567.8        7.5"
"\n  19     16     8       32     52.8     506.9        9.6"
"\n  20     16     8       38     48.5     552.9       11.4"
"\n  21     16     8       44     42.8     565.0       13.2"
"\n  22     16     8       51     37.1     567.6       15.3"
"\n  23     16     8       64     30.3     581.8       19.2"
"\n  24     16     8       76     25.7     586.0       22.8"
"\n  25     16     8       89     21.7     579.4       26.7"
"\n  26     16     8      102     19.3     590.6       30.6"
"\n  27     16     8      305      7.1     649.7       91.5"
"\n----------------------------------------------------------"
"\n HEAVY  <MORE> -press any key- ^See the Top:"
);princ
);strcat
(grread)
(princ
(strcat
"\n <20x10>--------------------------------------------------"
"\n  28     20    10       25    216.0    1620.0        7.5"
"\n  29     20    10       32    168.0    1612.8        9.6"
"\n  30     20    10       38    129.0    1419.0       11.0"
"\n  31     20    10       44    112.0    1456.0       13.0"
"\n  32     20    10       51     94.0    1410.0       15.0"
"\n  33     20    10       64     72.1    1369.9       19.0"
"\n  34     20    10       76     59.7    1373.1       23.0"
"\n  35     20    10       89     50.5    1363.5       27.0"
"\n  36     20    10      102     44.2    1370.2       31.0"
"\n  37     20    10      115     38.4    1344.0       35.0"
"\n  38     20    10      127     34.1    1295.8       38.0"
"\n  39     20    10      139     31.0    1302.0       42.0"
"\n  40     20    10      152     28.2    1297.2       46.0"
"\n  41     20    10      305     15.0    1365.0       91.0"
"\n <25x12.5>------------------------------------------------"
"\n  42     25    12.5     25    375.0    2812.5        7.5"
"\n  43     25    12.5     32    297.0    2851.2        9.6"
"\n  44     25    12.5     38    219.0    2409.0       11.0"
"\n  45     25    12.5     44    187.0    2431.0       13.0"
"\n  46     25    12.5     51    156.0    2340.0       15.0"
"\n  47     25    12.5     64    123.0    2337.0       19.0"
"\n  48     25    12.5     76     99.0    2277.0       23.0"
"\n  49     25    12.5     89     84.0    2268.0       27.0"
"\n  50     25    12.5    102     73.0    2263.0       31.0"
"\n  51     25    12.5    115     65.0    2275.0       35.0"
"\n  52     25    12.5    127     57.7    2192.6       38.0"
"\n  53     25    12.5    139     52.7    2213.4       42.0"
"\n  54     25    12.5    152     47.8    2198.8       46.0"
"\n  55     25    12.5    178     41.0    2173.0       53.0"
"\n  56     25    12.5    203     35.8    2183.8       61.0"
"\n  57     25    12.5    305     22.9    2083.9       91.0"
"\n <32x16>--------------------------------------------------"
"\n  58     32    16       38    388.0    4268.0       11.0"
"\n  59     32    16       44    324.0    4212.0       13.0"
"\n  60     32    16       51    272.0    4080.0       15.0"
"\n  61     32    16       64    212.0    4028.0       19.0"
"\n  62     32    16       76    172.0    3956.0       23.0"
"\n  63     32    16       89    141.0    3807.0       27.0"
"\n  64     32    16      102    122.0    3782.0       31.0"
"\n  65     32    16      115    107.0    3745.0       35.0"
"\n  66     32    16      127     93.0    3534.0       38.0"
"\n  67     32    16      139     86.0    3612.0       42.0"
"\n  68     32    16      152     78.0    3588.0       46.0"
"\n  69     32    16      178     67.2    3561.6       53.0"
"\n  70     32    16      203     59.1    3605.1       61.0"
"\n  71     32    16      254     46.4    3526.4       76.0"
"\n  72     32    16      305     38.0    3458.0       91.0"
"\n---------------------------------------------------------"
"\n HEAVY <MORE> -press any key- ^See the Top:"
);princ
);strcat
(grread)
(princ
(strcat
"\n <40x20>--------------------------------------------------"
"\n  73     40    20       51    350.0    5250.0       15.0"
"\n  74     40    20       64    269.0    5111.0       19.0"
"\n  75     40    20       76    219.0    5037.0       23.0"
"\n  76     40    20       89    190.0    5130.0       27.0"
"\n  77     40    20      102    163.0    5053.0       31.0"
"\n  78     40    20      115    142.0    4970.0       35.0"
"\n  79     40    20      127    128.0    4864.0       38.0"
"\n  80     40    20      139    115.0    4830.0       42.0"
"\n  81     40    20      152    105.0    4830.0       46.0"
"\n  82     40    20      178     89.0    4717.0       53.0"
"\n  83     40    20      203     77.0    4697.0       61.0"
"\n  84     40    20      254     61.0    4636.0       76.0"
"\n  85     40    20      305     51.0    4641.0       91.0"
"\n <50x25>--------------------------------------------------"
"\n  86     50    25       64    413.0    7847.0       19.0"
"\n  87     50    25       76    339.0    7797.0       23.0"
"\n  88     50    25       89    288.0    7776.0       27.0"
"\n  89     50    25      102    245.0    7595.0       31.0"
"\n  90     50    25      115    215.0    7525.0       35.0"
"\n  91     50    25      127    192.0    7296.0       38.0"
"\n  92     50    25      139    168.0    7056.0       42.0"
"\n  93     50    25      152    154.0    7084.0       46.0"
"\n  94     50    25      178    134.0    7102.0       53.0"
"\n  95     50    25      203    117.0    7137.0       61.0"
"\n  96     50    25      254     89.0    6764.0       76.0"
"\n  97     50    25      305     73.0    6643.0       91.0"
"\n HEAVY <END> See the Top=================================="      
);princ
);strcat
(setq an1 (getint "\nSelect No.: "))	;MENU/heavy
(cond
((= an1 1) (setq size '(10 5 25 22.1 165.8 7.5)))
((= an1 2) (setq size '(10 5 32 17.5 168.0 9.6)))
((= an1 3) (setq size '(10 5 38 17.1 194.9 11.4)))
((= an1 4) (setq size '(10 5 44 15.0 198.0 13.2)))
((= an1 5) (setq size '(10 5 51 12.8 195.8 15.3)))
((= an1 6) (setq size '(10 5 64 10.7 205.4 19.2)))
((= an1 7) (setq size '(10 5 76 7.5 171.0 22.8)))
((= an1 8) (setq size '(10 5 305 2.1 192.2 91.5)))
				;
((= an1 9) (setq size '(12.5 6.3 25 42.1 315.8 7.5)))
((= an1 10) (setq size '(12.5 6.3 32 33.2 318.7 9.6)))
((= an1 11) (setq size '(12.5 6.3 38 29.3 334.0 11.4)))
((= an1 12) (setq size '(12.5 6.3 44 24.6 324.7 13.2)))
((= an1 13) (setq size '(12.5 6.3 51 19.6 299.9 15.3)))
((= an1 14) (setq size '(12.5 6.3 64 15.0 288.0 19.2)))
((= an1 15) (setq size '(12.5 6.3 76 13.2 301.0 22.8)))
((= an1 16) (setq size '(12.5 6.3 89 11.4 304.4 26.7)))
((= an1 17) (setq size '(12.5 6.3 305 2.8 256.2 91.5)))
				;
((= an1 18) (setq size '(16 8 25 75.7 567.8 7.5)))
((= an1 19) (setq size '(16 8 32 52.8 506.9 9.6)))
((= an1 20) (setq size '(16 8 38 48.5 552.9 11.4)))
((= an1 21) (setq size '(16 8 44 42.8 565.0 13.2)))
((= an1 22) (setq size '(16 8 51 37.1 567.6 15.3)))
((= an1 23) (setq size '(16 8 64 30.3 581.8 19.2)))
((= an1 24) (setq size '(16 8 76 25.7 586.0 22.8)))
((= an1 25) (setq size '(16 8 89 21.7 579.4 26.7)))
((= an1 26) (setq size '(16 8 102 19.3 590.6 30.6)))
((= an1 27) (setq size '(16 8 305 7.1 649.7 91.5)))
				;
((= an1 28) (setq size '(20 10 25 216.0 1620.0 7.5)))
((= an1 29) (setq size '(20 10 32 168.0 1612.8 9.6)))
((= an1 30) (setq size '(20 10 38 129.0 1419.0 11.0)))
((= an1 31) (setq size '(20 10 44 112.0 1456.0 13.0)))
((= an1 32) (setq size '(20 10 51 94.0 1410.0 15.0)))
((= an1 33) (setq size '(20 10 64 72.1 1369.9 19.0)))
((= an1 34) (setq size '(20 10 76 59.7 1373.1 23.0)))
((= an1 35) (setq size '(20 10 89 50.5 1363.5 27.0)))
((= an1 36) (setq size '(20 10 102 44.2 1370.2 31.0)))
((= an1 37) (setq size '(20 10 115 38.4 1344.0 35.0)))
((= an1 38) (setq size '(20 10 127 34.1 1295.8 38.0)))
((= an1 39) (setq size '(20 10 139 31.0 1302.0 42.0)))
((= an1 40) (setq size '(20 10 152 28.2 1297.2 46.0)))
((= an1 41) (setq size '(20 10 305 15.0 1365.0 91.0)))
				;
((= an1 42) (setq size '(25 12.5 25 375.0 2812.5 7.5)))
((= an1 43) (setq size '(25 12.5 32 297.0 2851.2 9.6)))
((= an1 44) (setq size '(25 12.5 38 219.0 2409.0 11.0)))
((= an1 45) (setq size '(25 12.5 44 187.0 2431.0 13.0)))
((= an1 46) (setq size '(25 12.5 51 156.0 2340.0 15.0)))
((= an1 47) (setq size '(25 12.5 64 123.0 2337.0 19.0)))
((= an1 48) (setq size '(25 12.5 76 99.0 2277.0 23.0)))
((= an1 49) (setq size '(25 12.5 89 84.0 2268.0 27.0)))
((= an1 50) (setq size '(25 12.5 102 73.0 2263.0 31.0)))
((= an1 51) (setq size '(25 12.5 115 65.0 2275.0 35.0)))
((= an1 52) (setq size '(25 12.5 127 57.7 2192.6 38.0)))
((= an1 53) (setq size '(25 12.5 139 52.7 2213.4 42.0)))
((= an1 54) (setq size '(25 12.5 152 47.8 2198.8 46.0)))
((= an1 55) (setq size '(25 12.5 178 41.0 2173.0 53.0)))
((= an1 56) (setq size '(25 12.5 203 35.8 2183.8 61.0)))
((= an1 57) (setq size '(25 12.5 305 22.9 2083.9 91.0)))
				;
((= an1 58) (setq size '(32 16 38 388.0 4268.0 11.0)))
((= an1 59) (setq size '(32 16 44 324.0 4212.0 13.0)))
((= an1 60) (setq size '(32 16 51 272.0 4080.0 15.0)))
((= an1 61) (setq size '(32 16 64 212.0 4028.0 19.0)))
((= an1 62) (setq size '(32 16 76 172.0 3956.0 23.0)))
((= an1 63) (setq size '(32 16 89 141.0 3807.0 27.0)))
((= an1 64) (setq size '(32 16 102 122.0 3782.0 31.0)))
((= an1 65) (setq size '(32 16 115 107.0 3745.0 35.0)))
((= an1 66) (setq size '(32 16 127 93.0 3534.0 38.0)))
((= an1 67) (setq size '(32 16 139 86.0 3612.0 42.0)))
((= an1 68) (setq size '(32 16 152 78.0 3588.0 46.0)))
((= an1 69) (setq size '(32 16 178 67.2 3561.6 53.0)))
((= an1 70) (setq size '(32 16 203 59.1 3605.1 61.0)))
((= an1 71) (setq size '(32 16 254 46.4 3526.4 76.0)))
((= an1 72) (setq size '(32 16 305 38.0 3458.0 91.0)))
				;
((= an1 73) (setq size '(40 20 51 350.0 5250.0 15.0)))
((= an1 74) (setq size '(40 20 64 269.0 5111.0 19.0)))
((= an1 75) (setq size '(40 20 76 219.0 5037.0 23.0)))
((= an1 76) (setq size '(40 20 89 190.0 5130.0 27.0)))
((= an1 77) (setq size '(40 20 102 163.0 5053.0 31.0)))
((= an1 78) (setq size '(40 20 115 142.0 4970.0 35.0)))
((= an1 79) (setq size '(40 20 127 128.0 4864.0 38.0)))
((= an1 80) (setq size '(40 20 139 115.0 4830.0 42.0)))
((= an1 81) (setq size '(40 20 152 105.0 4830.0 46.0)))
((= an1 82) (setq size '(40 20 178 89.0 4717.0 53.0)))
((= an1 83) (setq size '(40 20 203 77.0 4697.0 61.0)))
((= an1 84) (setq size '(40 20 254 61.0 4636.0 76.0)))
((= an1 85) (setq size '(40 20 305 51.0 4641.0 91.0)))
				;
((= an1 86) (setq size '(50 25 64 413.0 7847.0 19.0)))
((= an1 87) (setq size '(50 25 76 339.0 7797.0 23.0)))
((= an1 88) (setq size '(50 25 89 288.0 7776.0 27.0)))
((= an1 89) (setq size '(50 25 102 245.0 7595.0 31.0)))
((= an1 90) (setq size '(50 25 115 215.0 7525.0 35.0)))
((= an1 91) (setq size '(50 25 127 192.0 7296.0 38.0)))
((= an1 92) (setq size '(50 25 139 168.0 7056.0 42.0)))
((= an1 93) (setq size '(50 25 152 154.0 7084.0 46.0)))
((= an1 94) (setq size '(50 25 178 134.0 7102.0 53.0)))
((= an1 95) (setq size '(50 25 203 117.0 7137.0 61.0)))
((= an1 96) (setq size '(50 25 254 89.0 6764.0 76.0)))
((= an1 97) (setq size '(50 25 305 73.0 6643.0 91.0)))
);cond
);defun/DIESPRING-HEAVY
-------------------------------------------------------------------------------
(defun DIESPRING-EXTRA ()
(princ
(strcat
"\n================================================================"
"\n                    CORE SPRING (EXTRA)              ISO"
"\n================================================================"
"\n   No.선택시 kg으로 환산 (1N/mm=0.102kg/mm / 1N=0.102kg)"
"\n----------------------------------------------------------------"
"\n   No.   O.D   I.D      H      RATE      MAX.        MAX."
"\n        (mm)   (mm)    (mm)   (N/mm)    LOAD(N)  DEFLECTION(mm)"
"\n <10x5>---------------------------------------------------------"
"\n   1     10     5       25     36.8     228.2       6.2"
"\n   2     10     5       32     27.9     223.2       8.0"
"\n   3     10     5       38     23.7     225.2       9.5"
"\n   4     10     5       44     19.2     211.2      11.0"
"\n   5     10     5       51     16.5     214.5      13.0"
"\n   6     10     5       64     13.2     211.2      16.0"
"\n   7     10     5       76     10.9     207.1      19.0"
"\n   8     10     5      305      2.6     197.6      76.0"
"\n <12.5x6.3>----------------------------------------------"
"\n   9     12.5   6.3     25     58.5     362.7       6.2"
"\n  10     12.5   6.3     32     43.9     351.2       8.0"
"\n  11     12.5   6.3     38     36.0     342.0       9.5"
"\n  12     12.5   6.3     44     30.3     333.3      11.0"
"\n  13     12.5   6.3     51     26.2     340.6      13.0"
"\n  14     12.5   6.3     64     21.2     339.2      16.0"
"\n  15     12.5   6.3     76     17.1     324.9      19.0"
"\n  16     12.5   6.3     89     14.5     319.0      22.0"
"\n  17     12.5   6.3    305      4.3     326.8      76.0"
"\n <16x8>--------------------------------------------------"
"\n  18     16     8       25    118.0     731.6       6.2"
"\n  19     16     8       32     89.0     712.0       8.0"
"\n  20     16     8       38     72.1     685.0       9.5"
"\n  21     16     8       44     60.9     669.9      11.0"
"\n  22     16     8       51     52.3     679.9      13.0"
"\n  23     16     8       64     41.2     659.2      16.0"
"\n  24     16     8       76     34.1     647.9      19.0"
"\n  25     16     8       89     29.5     649.0      22.0"
"\n  26     16     8      102     25.6     665.6      26.0"
"\n  27     16     8      305      8.4     638.4      76.0"
"\n---------------------------------------------------------"
"\n EXTRA <MORE> -press any key- ^See the Top"
);princ
);strcat
(grread)
(princ
(strcat
"\n <20x10>-------------------------------------------------"
"\n  28     20    10       25    293.0    1816.6       6.2"
"\n  29     20    10       32    224.0    1792.0       8.0"
"\n  30     20    10       38    177.0    1681.5       9.5"
"\n  31     20    10       44    149.0    1639.0      11.0"
"\n  32     20    10       51    128.0    1664.0      13.0"
"\n  33     20    10       64     99.0    1584.0      16.0"
"\n  34     20    10       76     81.7    1552.3      19.0"
"\n  35     20    10       89     69.5    1529.0      22.0"
"\n  36     20    10      102     60.6    1575.6      26.0"
"\n  37     20    10      115     53.0    1537.0      29.0"
"\n  38     20    10      127     47.5    1520.0      32.0"
"\n  39     20    10      139     43.0    1505.0      35.0"
"\n  40     20    10      152     39.0    1482.0      38.0"
"\n  41     20    10      305     21.2    1611.2      76.0"
"\n <25x12.5>-----------------------------------------------"
"\n  42     25    12.5     32    374.4    2995.2       8.0"
"\n  43     25    12.5     38    346.0    3287.0       9.5"
"\n  44     25    12.5     44    244.0    2684.0      11.0"
"\n  45     25    12.5     51    207.5    2697.5      13.0"
"\n  46     25    12.5     64    161.0    2576.0      16.0"
"\n  47     25    12.5     76    130.8    2485.2      19.0"
"\n  48     25    12.5     89    110.5    2431.0      22.0"
"\n  49     25    12.5    102     96.3    2503.8      26.0"
"\n  50     25    12.5    115     85.7    2485.3      29.0"
"\n  51     25    12.5    127     76.3    2441.6      32.0"
"\n  52     25    12.5    152     63.5    2413.0      38.0"
"\n  53     25    12.5    178     53.9    2371.6      44.0"
"\n  54     25    12.5    203     47.0    2397.0      51.0"
"\n  55     25    12.5    305     30.9    2348.4      76.0"
"\n <32x16>-------------------------------------------------"
"\n  56     32    16       38    528.2    5017.9       9.5"
"\n  57     32    16       44    424.4    4668.4      11.0"
"\n  58     32    16       51    353.0    4589.0      13.0"
"\n  59     32    16       64    269.2    4307.2      16.0"
"\n  60     32    16       76    218.5    4151.5      19.0"
"\n  61     32    16       89    180.3    3966.6      22.0"
"\n  62     32    16      102    155.0    4030.0      26.0"
"\n  63     32    16      115    140.0    4060.0      29.0"
"\n  64     32    16      127    124.0    3968.0      32.0"
"\n  65     32    16      152    102.0    3876.0      38.0"
"\n  66     32    16      178     88.2    3880.8      44.0"
"\n  67     32    16      203     76.0    3876.0      51.0"
"\n  68     32    16      254     60.8    3891.2      64.0"
"\n  69     32    16      305     49.0    3724.0      76.0"
"\n--------------------------------------------------------"
"\n EXTRA <MORE> -press any key- ^See the Top:"
);princ
);strcat
(grread)
(princ
(strcat
"\n <40x20>-------------------------------------------------"
"\n  70     40    20       51    628.0    8164.0      13.0"
"\n  71     40    20       64    487.0    7792.0      16.0"
"\n  72     40    20       76    379.0    7201.0      19.0"
"\n  73     40    20       89    321.0    7062.0      22.0"
"\n  74     40    20      102    281.0    7306.0      26.0"
"\n  75     40    20      115    245.0    7105.0      29.0"
"\n  76     40    20      127    221.0    7072.0      32.0"
"\n  77     40    20      152    168.0    6384.0      38.0"
"\n  78     40    20      178    146.0    6497.0      45.0"
"\n  79     40    20      203    132.0    6732.0      51.0"
"\n  80     40    20      254    107.0    6848.0      64.0"
"\n  81     40    20      305     87.8    6672.8      76.0"
"\n <50x25>-------------------------------------------------"
"\n  82     50    25       64    709.0   11344.0      16.0"
"\n  83     50    25       76    572.0   10868.0      19.0"
"\n  84     50    25       89    475.0   10450.0      22.0"
"\n  85     50    25      102    405.0   10530.0      26.0"
"\n  86     50    25      115    352.0   10208.0      29.0"
"\n  87     50    25      127    316.0   10112.0      32.0"
"\n  88     50    25      152    239.0    9082.0      38.0"
"\n  89     50    25      178    215.0    9568.0      45.0"
"\n  90     50    25      203    187.0    9537.0      51.0"
"\n  91     50    25      254    153.0    9792.0      64.0"
"\n  92     50    25      305    127.0    9652.0      76.0"
"\n EXTRA <END> See the Top================================="
);princ
);strcat
(setq an1 (getint "\nSelect No.: "))	;list/extra
(cond
((= an1 1) (setq size '(10 5 25 36.8 228.2 6.2)))
((= an1 2) (setq size '(10 5 32 27.9 223.2 8.0)))
((= an1 3) (setq size '(10 5 38 23.7 225.2 9.5)))
((= an1 4) (setq size '(10 5 44 19.2 211.2 11.0)))
((= an1 5) (setq size '(10 5 51 16.5 214.5 13.0)))
((= an1 6) (setq size '(10 5 64 13.2 211.2 16.0)))
((= an1 7) (setq size '(10 5 76 10.9 207.1 19.0)))
((= an1 8) (setq size '(10 5 305 2.6 197.6 76.0)))
				;
((= an1 9) (setq size '(12.5 6.3 25 58.5 362.7 6.2)))
((= an1 10) (setq size '(12.5 6.3 32 43.9 351.2 8.0)))
((= an1 11) (setq size '(12.5 6.3 38 36.0 342.0 9.5)))
((= an1 12) (setq size '(12.5 6.3 44 30.3 333.3 11.0)))
((= an1 13) (setq size '(12.5 6.3 51 26.2 340.6 13.0)))
((= an1 14) (setq size '(12.5 6.3 64 21.2 339.2 16.0)))
((= an1 15) (setq size '(12.5 6.3 76 17.1 324.9 19.0)))
((= an1 16) (setq size '(12.5 6.3 89 14.5 319.0 22.0)))
((= an1 17) (setq size '(12.5 6.3 305 4.3 326.8 76.0)))
				;
((= an1 18) (setq size '(16 8 25 118.0 731.6 6.2)))
((= an1 19) (setq size '(16 8 32 89.0 712.0 8.0)))
((= an1 20) (setq size '(16 8 38 72.1 685.0 9.5)))
((= an1 21) (setq size '(16 8 44 60.9 669.9 11.0)))
((= an1 22) (setq size '(16 8 51 52.3 679.9 13.0)))
((= an1 23) (setq size '(16 8 64 41.2 659.2 16.0)))
((= an1 24) (setq size '(16 8 76 34.1 647.9 19.0)))
((= an1 25) (setq size '(16 8 89 29.5 649.0 22.0)))
((= an1 26) (setq size '(16 8 102 25.6 665.6 26.0)))
((= an1 27) (setq size '(16 8 305 8.4 638.4 76.0)))
				;
((= an1 28) (setq size '(20 10 25 293.0 1816.6 6.2)))
((= an1 29) (setq size '(20 10 32 224.0 1792.0 8.0)))
((= an1 30) (setq size '(20 10 38 177.0 1681.5 9.5)))
((= an1 31) (setq size '(20 10 44 149.0 1639.0 11.0)))
((= an1 32) (setq size '(20 10 51 128.0 1664.0 13.0)))
((= an1 33) (setq size '(20 10 64 99.0 1584.0 16.0)))
((= an1 34) (setq size '(20 10 76 81.7 1552.3 19.0)))
((= an1 35) (setq size '(20 10 89 69.5 1529.0 22.0)))
((= an1 36) (setq size '(20 10 102 60.6 1575.6 26.0)))
((= an1 37) (setq size '(20 10 115 53.0 1537.0 29.0)))
((= an1 38) (setq size '(20 10 127 47.5 1520.0 32.0)))
((= an1 39) (setq size '(20 10 139 43.0 1505.0 35.0)))
((= an1 40) (setq size '(20 10 152 39.0 1482.0 38.0)))
((= an1 41) (setq size '(20 10 305 21.2 1611.2 76.0)))
				;
((= an1 42) (setq size '(25 12.5 32 374.4 2995.2 8.0)))
((= an1 43) (setq size '(25 12.5 38 346.0 3287.0 9.5)))
((= an1 44) (setq size '(25 12.5 44 244.0 2684.0 11.0)))
((= an1 45) (setq size '(25 12.5 51 207.5 2697.5 13.0)))
((= an1 46) (setq size '(25 12.5 64 161.0 2576.0 16.0)))
((= an1 47) (setq size '(25 12.5 76 130.8 2485.2 19.0)))
((= an1 48) (setq size '(25 12.5 89 110.5 2431.0 22.0)))
((= an1 49) (setq size '(25 12.5 102 96.3 2503.8 26.0)))
((= an1 50) (setq size '(25 12.5 115 85.7 2485.3 29.0)))
((= an1 51) (setq size '(25 12.5 127 76.3 2441.6 32.0)))
((= an1 52) (setq size '(25 12.5 152 63.5 2413.0 38.0)))
((= an1 53) (setq size '(25 12.5 178 53.9 2371.6 44.0)))
((= an1 54) (setq size '(25 12.5 203 47.0 2397.0 51.0)))
((= an1 55) (setq size '(25 12.5 305 30.9 2348.4 76.0)))
				;
((= an1 56) (setq size '(32 16 38 528.2 5017.9 9.5)))
((= an1 57) (setq size '(32 16 44 424.4 4668.4 11.0)))
((= an1 58) (setq size '(32 16 51 353.0 4589.0 13.0)))
((= an1 59) (setq size '(32 16 64 269.2 4307.2 16.0)))
((= an1 60) (setq size '(32 16 76 218.5 4151.5 19.0)))
((= an1 61) (setq size '(32 16 89 180.3 3966.6 22.0)))
((= an1 62) (setq size '(32 16 102 155.0 4030.0 26.0)))
((= an1 63) (setq size '(32 16 115 140.0 4060.0 29.0)))
((= an1 64) (setq size '(32 16 127 124.0 3968.0 32.0)))
((= an1 65) (setq size '(32 16 152 102.0 3876.0 38.0)))
((= an1 66) (setq size '(32 16 178 88.2 3880.8 44.0)))
((= an1 67) (setq size '(32 16 203 76.0 3876.0 51.0)))
((= an1 68) (setq size '(32 16 254 60.8 3891.2 64.0)))
((= an1 69) (setq size '(32 16 305 49.0 3724.0 76.0)))
				;
((= an1 70) (setq size '(40 20 51 628.0 8164.0 13.0)))
((= an1 71) (setq size '(40 20 64 487.0 7792.0 16.0)))
((= an1 72) (setq size '(40 20 76 379.0 7201.0 19.0)))
((= an1 73) (setq size '(40 20 89 321.0 7062.0 22.0)))
((= an1 74) (setq size '(40 20 102 281.0 7306.0 26.0)))
((= an1 75) (setq size '(40 20 115 245.0 7105.0 29.0)))
((= an1 76) (setq size '(40 20 127 221.0 7072.0 32.0)))
((= an1 77) (setq size '(40 20 152 168.0 6384.0 38.0)))
((= an1 78) (setq size '(40 20 178 146.0 6497.0 45.0)))
((= an1 79) (setq size '(40 20 203 132.0 6732.0 51.0)))
((= an1 80) (setq size '(40 20 254 107.0 6848.0 64.0)))
((= an1 81) (setq size '(40 20 305 87.8 6672.8 76.0)))
				;
((= an1 82) (setq size '(50 25 64 709.0 11344.0 16.0)))
((= an1 83) (setq size '(50 25 76 572.0 10868.0 19.0)))
((= an1 84) (setq size '(50 25 89 475.0 10450.0 22.0)))
((= an1 85) (setq size '(50 25 102 405.0 10530.0 26.0)))
((= an1 86) (setq size '(50 25 115 352.0 10208.0 29.0)))
((= an1 87) (setq size '(50 25 127 316.0 10112.0 32.0)))
((= an1 88) (setq size '(50 25 152 239.0 9082.0 38.0)))
((= an1 89) (setq size '(50 25 178 215.0 9568.0 45.0)))
((= an1 90) (setq size '(50 25 203 187.0 9537.0 51.0)))
((= an1 91) (setq size '(50 25 254 153.0 9792.0 64.0)))
((= an1 92) (setq size '(50 25 305 127.0 9652.0 76.0)))
);cond/extra
);defun/EXTRA
;-------------------------------------------------------------------------
(defun DIESPRING1-LIGHTEST ()
(princ
(strcat
"\n=================================================================="
"\n                     CORE SPRING  (LIGHTEST)"
"\n=================================================================="
"\n  I.D     O.D      H       RATE        MAX.           MAX."
"\n (mm)    (mm)     (mm)   (kgf/mm)  DEFLECTION(mm)   LOAD(kg)"
"\n <4X8>------------------------------------------------------------"
"\n   4     8        10       1.56        5.0           8.0 (78.5N)"
"\n                  15       1.04        7.5"
"\n                  20       0.78       10.0"
"\n                  25       0.62       12.5"
"\n                  30       0.52       15.0"
"\n                  35       0.44       17.5"
"\n                  40       0.39       20.0"
"\n                  45       0.35       22.5"
"\n                  50       0.31       25.0"
"\n                  55       0.28       27.5"
"\n                  60       0.26       30.0"
"\n                  65       0.24       32.5"
"\n                  70       0.22       35.0"
"\n                  75       0.21       37.5"
"\n                  80       0.19       40.0"
"\n <5X10>--------------------------------------------------------"
"\n   5     10       20       1.00       10.0         10 (98.1N)"
"\n                  25       0.80       12.5"
"\n                  30       0.67       15.0"
"\n                  35       0.57       17.5"
"\n                  40       0.50       20.0"
"\n                  45       0.44       22.5"
"\n                  50       0.40       25.0"
"\n                  55       0.36       27.5"
"\n                  60       0.33       30.0"
"\n                  65       0.31       32.5"
"\n                  70       0.29       35.0"
"\n                  75       0.27       37.5"
"\n                  80       0.25       40.0"
"\n                  90       0.22       45.0"
"\n <6X12>---------------------------------------------------------"
"\n   6     12       20       1.40       10.0         14 (137.3N)"
"\n                  25       1.12       12.5"
"\n                  30       0.93       15.0"
"\n                  35       0.80       17.5"
"\n                  40       0.70       20.0"
"\n                  45       0.62       22.5"
"\n                  50       0.56       25.0"
"\n                  55       0.51       27.5"
"\n                  60       0.47       30.0"
"\n                  65       0.43       32.5"
"\n                  70       0.40       35.0"
"\n                  75       0.37       37.5"
"\n                  80       0.35       40.0"
"\n                  90       0.31       45.0"
"\n----------------------------------------------------------------"
"\n LIGHTEST <MORE> -press any key- ^See the Top:"
);princ
);strcat
(grread)
(princ
(strcat
"\n <7X14>--------------------------------------------------------"
"\n   7     14       25       1.44       12.5        18 (176.5N)"
"\n                  30       1.20       15.0"
"\n                  40       0.90       20.0"
"\n                  45       0.80       22.5"
"\n                  50       0.72       25.0"
"\n                  55       0.65       27.5"
"\n                  60       0.60       30.0"
"\n                  65       0.55       32.5"
"\n                  70       0.51       35.0"
"\n                  75       0.48       37.5"
"\n                  80       0.45       40.0"
"\n                  90       0.40       45.0"
"\n                 100       0.36       50.0"
"\n <8X16>------------------------------------------------------"
"\n    8    16       25       1.68       12.5        21 (206N)"
"\n                  30       1.40       15.0"
"\n                  35       1.20       17.5"
"\n                  40       1.05       20.0"
"\n                  45       0.94       22.5"
"\n                  50       0.84       25.0"
"\n                  55       0.77       27.5"
"\n                  60       0.70       30.0"
"\n                  65       0.65       32.5"
"\n                  70       0.60       35.0"
"\n                  75       0.56       37.5"
"\n                  80       0.53       40.0"
"\n                  90       0.47       45.0"
"\n                 100       0.42       50.0"
"\n                 125       0.34       62.5"
"\n <9X18>------------------------------------------------------"
"\n   9     18       25       2.08       12.5        26 (255N)"
"\n                  30       1.74       15.0"
"\n                  35       1.49       17.5"
"\n                  40       1.30       20.0"
"\n                  45       1.16       22.5"
"\n                  50       1.04       25.0"
"\n                  55       0.95       27.5"
"\n                  60       0.87       30.0"
"\n                  65       0.80       32.5"
"\n                  70       0.74       35.0"
"\n                  75       0.70       37.5"
"\n                  80       0.65       40.0"
"\n                  90       0.58       45.0"
"\n                 100       0.52       50.0"
"\n                 125       0.41       62.5"
"\n------------------------------------------------------------"
"\n LIGHTEST <MORE> -press any key- ^See the Top:"
);princ
);strcat
(grread)
(princ
(strcat
"\n <11X20>----------------------------------------------------"
"\n    11    20      25       2.56       12.5       32 (314N)"
"\n                  30       2.13       15.0"
"\n                  35       1.83       17.5"
"\n                  40       1.60       20.0"
"\n                  45       1.42       22.5"
"\n                  50       1.28       25.0"
"\n                  55       1.16       27.5"
"\n                  60       1.07       30.0"
"\n                  65       0.98       32.5"
"\n                  70       0.91       35.0"
"\n                  75       0.85       37.5"
"\n                  80       0.80       40.0"
"\n                  90       0.71       45.0"
"\n                 100       0.64       50.0"
"\n                 125       0.51       62.5"
"\n                 150       0.43       75.0"
"\n <11X22>----------------------------------------------------"
"\n    11    22      25       3.20       12.5       40 (392N)"
"\n                  30       2.67       15.0"
"\n                  35       2.29       17.5"
"\n                  40       2.00       20.0"
"\n                  45       1.78       22.5"
"\n                  50       1.60       25.0"
"\n                  55       1.46       27.5"
"\n                  60       1.33       30.0"
"\n                  65       1.23       32.5"
"\n                  70       1.14       35.0"
"\n                  75       1.07       37.5"
"\n                  80       1.00       40.0"
"\n                  90       0.89       45.0"
"\n                 100       0.80       50.0"
"\n                 125       0.64       62.5"
"\n                 150       0.53       75.0"
"\n <13.5X25>--------------------------------------------------"
"\n    13.5    25    25       4.00       12.5       50 (490N)"
"\n                  30       3.33       15.0"
"\n                  35       2.85       17.5"
"\n                  40       2.50       20.0"
"\n                  45       2.22       22.5"
"\n                  50       2.00       25.0"
"\n                  55       1.82       27.5"
"\n                  60       1.67       30.0"
"\n                  65       1.54       32.5"
"\n                  75       1.33       37.5"
"\n                  80       1.25       40.0"
"\n                  90       1.11       45.0"
"\n                 100       1.00       50.0"
"\n                 125       0.80       62.5"
"\n                 150       0.67       75.0"
"\n                 175       0.57       87.5"
"\n                 200       0.50      100.0"
"\n------------------------------------------------------------"
"\n LIGHTEST <MORE> -press any key- ^See the Top:"
);princ
);strcat
(grread)
(princ
(strcat
"\n <13.5X27>---------------------------------------------------"
"\n    13.5    27    25       4.80       12.5        60 (588N)"
"\n                  30       4.00       15.0"
"\n                  35       3.43       17.5"
"\n                  40       3.00       20.0"
"\n                  45       2.67       22.5"
"\n                  50       2.40       25.0"
"\n                  55       2.18       27.5"
"\n                  60       2.00       30.0"
"\n                  65       1.85       32.5"
"\n                  70       1.71       35.0"
"\n                  75       1.60       37.5"
"\n                  80       1.50       40.0"
"\n                  90       1.33       45.0"
"\n                 100       1.20       50.0"
"\n                 125       0.96       62.5"
"\n                 150       0.80       75.0"
"\n                 175       0.69       87.5"
"\n                 200       0.60      100.0"
"\n <16X30>-----------------------------------------------------"
"\n   16     30      25       5.80       12.5        72 (706N)"
"\n                  30       4.80       15.0"
"\n                  35       4.13       17.5"
"\n                  40       3.60       20.0"
"\n                  45       3.21       22.5"
"\n                  50       2.88       25.0"
"\n                  55       2.63       27.5"
"\n                  60       2.40       30.0"
"\n                  65       2.22       32.5"
"\n                  70       2.05       35.0"
"\n                  75       1.93       37.5"
"\n                  80       1.80       40.0"
"\n                  90       1.60       45.0"
"\n                 100       1.44       50.0"
"\n                 125       1.15       62.5"
"\n                 150       0.96       75.0"
"\n                 175       0.82       87.5"
"\n                 200       0.72      100.0"
"\n <16X30>------------------------------------------------------"
"\n    16    30      30       6.7        12.0       81 (794.1N)"
"\n                  35       5.7        14.0"
"\n                  40       5.0        16.0"
"\n                  45       4.4        18.0"
"\n                  50       4.0        20.0"
"\n                  55       3.6        22.0"
"\n                  60       3.3        24.0"
"\n                  65       3.1        26.0"
"\n                  70       2.9        28.0"
"\n                  75       2.7        30.0"
"\n                  80       2.5        32.0"
"\n                  90       2.2        36.0"
"\n                 100       2.0        40.0"
"\n                 125       1.6        50.0"
"\n                 150       1.3        60.0"
"\n                 175       1.1        70.0"
"\n--------------------------------------------------------------"
"\n LIGHTEST <MORE> -press any key- ^See the Top:"
);princ
);strcat
(grread)
(princ
(strcat
"\n <20X35>------------------------------------------------------"
"\n    20    35      40       5.4        16.0       86 (843.1N)"
"\n                  45       4.8        18.0"
"\n                  50       4.3        20.0"
"\n                  55       3.9        22.0"
"\n                  60       3.6        24.0"
"\n                  65       3.3        26.0"
"\n                  70       3.1        28.0"
"\n                  75       2.9        30.0"
"\n                  80       2.7        32.0"
"\n                  90       2.4        36.0"
"\n                 100       2.2        40.0"
"\n                 125       1.7        50.0"
"\n                 150       1.4        60.0"
"\n                 175       1.2        70.0"
"\n                 200       1.1        80.0"
"\n <19X35>-----------------------------------------------------"
"\n   19     35      40       4.90       20.0        98 (961N)"
"\n                  45       4.36       22.5"
"\n                  50       3.92       25.0"
"\n                  55       3.56       27.5"
"\n                  60       3.26       30.0"
"\n                  65       3.02       32.5"
"\n                  70       2.80       35.0"
"\n                  75       2.61       37.5"
"\n                  80       2.45       40.0"
"\n                  90       2.17       45.0"
"\n                 100       1.96       50.0"
"\n                 125       1.57       62.5"
"\n                 150       1.30       75.0"
"\n                 175       1.12       87.5"
"\n                 200       0.98      100.0"
"\n <22X40>------------------------------------------------------"
"\n   22     40      40       6.38       20.0      128 (1,255N)"
"\n                  45       5.68       22.5"
"\n                  50       5.12       25.0"
"\n                  55       4.65       27.5"
"\n                  60       4.26       30.0"
"\n                  65       3.93       32.5"
"\n                  70       3.65       35.0"
"\n                  75       3.41       37.5"
"\n                  80       3.20       40.0"
"\n                  90       2.84       45.0"
"\n                 100       2.56       50.0"
"\n                 125       2.04       62.5"
"\n                 150       1.70       75.0"
"\n                 175       1.46       87.5"
"\n                 200       1.28      100.0"
"\n                 250       1.02      125.0"
"\n                 275       0.93      137.5"
"\n                 300       0.85      150.0"
"\n--------------------------------------------------------------"
"\n LIGHTEST <MORE> -press any key- ^See the Top:"
);princ
);strcat
(grread)
(princ
(strcat
"\n <26X40>-------------------------------------------------------" 
"\n   26     40      50       8.70       20.0     174 (1,705.8N)"
"\n                  60       7.20       24.0"
"\n                  70       6.20       28.0"
"\n                  80       5.40       32.0"
"\n                  90       4.80       36.0"
"\n                 100       4.30       40.0"
"\n                 125       3.50       50.0"
"\n                 150       2.90       60.0"
"\n                 175       2.50       70.0"
"\n                 200       2.20       80.0"
"\n                 250       1.70      100.0"
"\n <27.5X50>---------------------------------------------------"
"\n   27.5     50    50       8.00       25.0     200 (1,961N)"
"\n                  55       7.27       27.5"
"\n                  60       6.66       30.0"
"\n                  65       6.15       32.5"
"\n                  70       5.71       35.0"
"\n                  75       5.33       37.5"
"\n                  80       5.00       40.0"
"\n                  90       4.44       45.0"
"\n                 100       4.00       50.0"
"\n                 125       3.20       62.5"
"\n                 150       2.66       75.0"
"\n                 175       2.28       87.5"
"\n                 200       2.00      100.0"
"\n                 225       1.78      112.5"
"\n                 250       1.60      125.0"
"\n                 275       1.45      137.5"
"\n                 300       1.33      150.0"
"\n                 350       1.14      175.0"
"\n                 400       1.00      200.0"
"\n                 450       0.89      225.0"
"\n                 500       0.80      250.0"
"\n <30X50>-------------------------------------------------------"
"\n   30     50      60      10.80       24.0       260 (2,549N)"
"\n                  70       9.30       28.0"
"\n                  80       8.10       32.0"
"\n                  90       7.20       36.0"
"\n                 100       6.40       40.0"
"\n                 125       5.20       50.0"
"\n                 150       4.30       60.0"
"\n                 175       3.70       70.0"
"\n                 200       3.30       80.0"
"\n                 250       2.60      100.0"
"\n                 300       2.20      120.0"
"\n                 350       1.90      140.0"
"\n                 400       1.60      160.0"
"\n                 450       1.40      180.0"
"\n                 500       1.30      200.0"
"\n---------------------------------------------------------------"
"\n LIGHTEST <MORE> -press any key- ^See the Top:"
);princ
);strcat
(grread)
(princ
(strcat      
"\n <33X60>-------------------------------------------------------"
"\n   33     60      60       9.59      30.0        288 (2,820N)"
"\n                  70       8.22      35.0"
"\n                  80       7.19      40.0"
"\n                  90       6.40      45.0"
"\n                 100       5.76      50.0"
"\n                 125       4.60      62.5"
"\n                 150       3.84      75.0"
"\n                 175       3.29      87.5"
"\n                 200       2.88     100.0"
"\n                 225       2.56     112.5"
"\n                 250       2.30     125.0"
"\n                 275       2.09     137.5"
"\n                 300       1.92     150.0"
"\n                 350       1.65     175.0"
"\n                 400       1.44     200.0"
"\n                 450       1.28     225.0"
"\n                 500       1.15     250.0"
"\n <35X60>---------------------------------------------------------"
"\n   35     60      70      13.10      28.0        370 (3,627.4N)"
"\n                  80      11.50      32.0"
"\n                  90      10.20      36.0"
"\n                 100       9.20      40.0"
"\n                 125       7.40      50.0"
"\n                 150       6.10      60.0"
"\n                 175       5.30      70.0"
"\n                 200       4.60      80.0"
"\n                 250       3.70     100.0"
"\n                 300       3.10     120.0"
"\n                 400       2.30     160.0"
"\n                 450       2.08     180.0"
"\n                 500       1.85     200.0"
"\n LIGHTEST <END> See the Top======================================="
);princ
);strcat  
);defun/Lighest end
;---------------------------------------------------------------------
(defun DIESPRING2-LIGHT () 
(princ
(strcat
"\n==================================================================="
"\n                      CORE SPRING  (LIGHT)"
"\n==================================================================="
"\n  I.D     O.D      H       RATE        MAX.           MAX."
"\n (mm)    (mm)     (mm)   (kgf/mm)  DEFLECTION(mm)   LOAD(kg)"
"\n <4X8>-------------------------------------------------------------"
"\n   4      8       10       2.50        4.0          10.00 (98.1N)"
"\n                  15       1.67        6.0"
"\n                  20       1.25        8.0"
"\n                  25       1.00       10.0"
"\n                  30       0.83       12.0"
"\n                  35       0.71       14.0"
"\n                  40       0.63       16.0"
"\n                  45       0.56       18.0"
"\n                  50       0.50       20.0"
"\n                  55       0.46       22.0"
"\n                  60       0.42       24.0"
"\n                  65       0.39       26.0"
"\n                  70       0.36       28.0"
"\n                  75       0.33       30.0"
"\n                  80       0.31       32.0"
"\n <5X10>------------------------------------------------------------"
"\n   5     10       20       1.81        8.0          14.5 (142.2N)"
"\n                  25       1.45       10.0"
"\n                  30       1.21       12.0"
"\n                  35       1.03       14.0"
"\n                  40       0.90       16.0"
"\n                  45       0.80       18.0"
"\n                  50       0.73       20.0"
"\n                  55       0.66       22.0"
"\n                  60       0.60       24.0"
"\n                  65       0.55       26.0"
"\n                  70       0.51       28.0"
"\n                  75       0.48       30.0"
"\n                  80       0.45       32.0"
"\n                  90       0.40       36.0"
"\n <6X12>------------------------------------------------------------"
"\n   6     12       20       2.63        8.0              21 (206N)"
"\n                  25       2.10       10.0"
"\n                  30       1.75       12.0"
"\n                  35       1.50       14.0"
"\n                  40       1.32       16.0"
"\n                  45       1.17       18.0"
"\n                  50       1.05       20.0"
"\n                  55       0.96       22.0"
"\n                  60       0.88       24.0"
"\n                  65       0.81       26.0"
"\n                  70       0.75       28.0"
"\n                  75       0.70       30.0"
"\n                  80       0.66       32.0"
"\n                  90       0.59       36.0"
"\n-------------------------------------------------------------------"
"\n LIGHT <MORE> -press any key- ^See the Top:"
);princ
);strcat
(grread)
(princ
(strcat 
"\n <7X14>------------------------------------------------------------"
"\n   7     14       25       2.80       10.0              28 (275N)"
"\n                  30       2.34       12.0"
"\n                  35       2.00       14.0"
"\n                  40       1.75       16.0"
"\n                  45       1.56       18.0"
"\n                  50       1.40       20.0"
"\n                  55       1.27       22.0"
"\n                  60       1.17       24.0"
"\n                  65       1.08       26.0"
"\n                  70       1.00       28.0"
"\n                  75       0.93       30.0"
"\n                  80       0.87       32.0"
"\n                  90       0.77       36.0"
"\n                 100       0.69       40.0"
"\n <8X16>---------------------------------------------------------"
"\n   8     16       25       3.50       10.0           35 (343N)"
"\n                  30       2.92       12.0"
"\n                  35       2.50       14.0"
"\n                  40       2.19       16.0"
"\n                  45       1.95       18.0"
"\n                  50       1.75       20.0"
"\n                  55       1.60       22.0"
"\n                  60       1.46       24.0"
"\n                  65       1.35       26.0"
"\n                  70       1.25       28.0"
"\n                  75       1.17       30.0"
"\n                  80       1.10       32.0"
"\n                  90       0.98       36.0"
"\n                 100       0.88       40.0"
"\n                 125       0.71       50.0"
"\n <9X18>---------------------------------------------------------"
"\n   9     18       25       4.30       10.0           43 (422N)"
"\n                  30       3.58       12.0"
"\n                  35       3.07       14.0"
"\n                  40       2.69       16.0"
"\n                  45       2.39       18.0"
"\n                  50       2.15       20.0"
"\n                  55       1.96       22.0"
"\n                  60       1.79       24.0"
"\n                  65       1.66       26.0"
"\n                  70       1.54       28.0"
"\n                  75       1.44       30.0"
"\n                  80       1.35       32.0"
"\n                  90       1.20       36.0"
"\n                 100       1.07       40.0"
"\n                 125       0.87       50.0"
"\n----------------------------------------------------------------"
"\n LIGHT <MORE> -press any key- ^See the Top:"
);princ
);strcat
(grread)
(princ
(strcat 
"\n <10X20>--------------------------------------------------------"
"\n   10     20      25       5.40       10.0           53 (530N)"
"\n                  30       4.50       12.0"
"\n                  35       3.86       14.0"
"\n                  40       3.38       16.0"
"\n                  45       3.00       18.0"
"\n                  50       2.70       20.0"
"\n                  55       2.45       22.0"
"\n                  60       2.25       24.0"
"\n                  65       2.08       26.0"
"\n                  70       1.93       28.0"
"\n                  75       1.80       30.0"
"\n                  80       1.69       32.0"
"\n                  90       1.50       36.0"
"\n                 100       1.35       40.0"
"\n                 125       1.08       50.0"
"\n                 150       0.90       60.0"
"\n <11X22>-------------------------------------------------------"
"\n   11     22      25       6.70       10.0          67 (657N)"
"\n                  30       5.60       12.0"
"\n                  35       4.80       14.0"
"\n                  40       4.20       16.0"
"\n                  45       3.72       18.0"
"\n                  50       3.35       20.0"
"\n                  55       3.05       22.0"
"\n                  60       2.80       24.0"
"\n                  65       2.58       26.0"
"\n                  70       2.40       28.0"
"\n                  75       2.23       30.0"
"\n                  80       2.10       32.0"
"\n                  90       1.86       36.0"
"\n                 100       1.68       40.0"
"\n                 125       1.34       50.0"
"\n                 150       1.12       60.0"
"\n <12.5X25>------------------------------------------------------"
"\n    12.5    25    25       8.40       10.0           84 (824N)"
"\n                  30       7.00       12.0"
"\n                  35       6.00       14.0"
"\n                  40       5.25       16.0"
"\n                  45       4.67       18.0"
"\n                  50       4.20       20.0"
"\n                  55       3.82       22.0"
"\n                  60       3.50       24.0"
"\n                  65       3.23       26.0"
"\n                  70       3.00       28.0"
"\n                  75       2.80       30.0"
"\n                  80       2.63       32.0"
"\n                  90       2.33       36.0"
"\n                 100       2.10       40.0"
"\n                 125       1.68       50.0"
"\n                 150       1.40       60.0"
"\n                 175       1.20       70.0"
"\n                 200       1.06       80.0"
"\n--------------------------------------------------------------"
"\n LIGHT <MORE> -press any key- ^See the Top:"
);princ
);strcat
(grread)
(princ
(strcat 
"\n <13.5X27>----------------------------------------------------"
"\n    13.5    27    25      10.00       10.0          100(981)"
"\n                  30       8.33       12.0"
"\n                  35       7.14       14.0"
"\n                  40       6.25       16.0"
"\n                  45       5.56       18.0"
"\n                  50       5.00       20.0"
"\n                  55       4.55       22.0"
"\n                  60       4.17       24.0"
"\n                  65       3.85       26.0"
"\n                  70       3.57       28.0"
"\n                  75       3.33       30.0"
"\n                  80       3.13       32.0"
"\n                  90       2.78       36.0"
"\n                 100       2.50       40.0"
"\n                 125       2.00       50.0"
"\n                 150       1.67       60.0"
"\n                 175       1.43       70.0"
"\n                 200       1.25       80.0"
"\n <15X30>---------------------------------------------------------"
"\n   15     30      25      12.11       10.0         121 (1,187N)"
"\n                  30      10.08       12.0"
"\n                  35       8.65       14.0"
"\n                  40       7.56       16.0"
"\n                  45       6.73       18.0"
"\n                  50       6.05       20.0"
"\n                  55       5.50       22.0"
"\n                  60       5.04       24.0"
"\n                  65       4.65       26.0"
"\n                  70       4.32       28.0"
"\n                  75       4.03       30.0"
"\n                  80       3.78       32.0"
"\n                  90       3.36       36.0"
"\n                 100       3.02       40.0"
"\n                 125       2.42       50.0"
"\n                 150       2.01       60.0"
"\n                 175       1.72       70.0"
"\n                 200       1.51       80.0"
"\n <17.5X35>--------------------------------------------------------"
"\n   17.5     35    40      10.31       16.0          165 (1,618N)"
"\n                  45       9.17       18.0"
"\n                  50       8.25       20.0"
"\n                  55       7.50       22.0"
"\n                  60       6.87       24.0"
"\n                  65       6.35       26.0"
"\n                  70       5.89       28.0"
"\n                  75       5.50       30.0"
"\n                  80       5.15       32.0"
"\n                  90       4.58       36.0"
"\n                 100       4.12       40.0"
"\n                 125       3.30       50.0"
"\n                 150       2.75       60.0"
"\n                 175       2.35       70.0"
"\n                 200       2.06       80.0"
"\n-----------------------------------------------------------------"
"\n LIGHT <MORE> -press any key- ^See the Top:"
);princ
);strcat
(grread)
(princ
(strcat 
"\n <20X40>---------------------------------------------------------"
"\n   20     40      40      13.50       16.0         216 (2,120N)"
"\n                  45      11.98       18.0"
"\n                  50      10.80       20.0"
"\n                  55       9.80       22.0"
"\n                  60       9.00       24.0"
"\n                  65       8.29       26.0"
"\n                  70       7.71       28.0"
"\n                  75       7.19       30.0"
"\n                  80       6.75       32.0"
"\n                  90       6.00       36.0"
"\n                 100       5.40       40.0"
"\n                 125       4.32       50.0"
"\n                 150       3.60       60.0"
"\n                 175       3.08       70.0"
"\n                 200       2.70       80.0"
"\n                 225       2.40       90.0"
"\n                 250       2.16      100.0"
"\n                 275       1.96      110.0"
"\n                 300       1.80      120.0"
"\n <25X50>---------------------------------------------------------"
"\n   25     50      50      16.89       20.0         338 (3,310N)"
"\n                  55      15.35       22.0"
"\n                  60      14.08       24.0"
"\n                  65      12.99       26.0"
"\n                  70      12.07       28.0"
"\n                  75      11.25       30.0"
"\n                  80      10.56       32.0"
"\n                  90       9.38       36.0"
"\n                 100       8.45       40.0"
"\n                 125       6.76       50.0"
"\n                 150       5.63       60.0"
"\n                 175       4.82       70.0"
"\n                 200       4.22       80.0"
"\n                 225       3.75       90.0"
"\n                 250       3.38      100.0"
"\n                 275       3.07      110.0"
"\n                 300       2.81      120.0"
"\n                 350       2.41      140.0"
"\n                 400       2.11      160.0"
"\n                 450       1.88      180.0"
"\n                 500       1.69      200.0"
"\n <30X60>---------------------------------------------------------"
"\n   30     60      60      20.25       24.0         486 (4,770N)"
"\n                  70      17.35       28.0"
"\n                  80      15.18       32.0"
"\n                  90      13.50       36.0"
"\n                 100      12.15       40.0"
"\n                 125       9.72       50.0"
"\n                 150       8.10       60.0"
"\n                 175       6.94       70.0"
"\n                 200       6.07       80.0"
"\n                 225       5.40       90.0"
"\n                 250       4.86      100.0"
"\n                 275       4.42      110.0"
"\n                 300       4.05      120.0"
"\n                 350       3.47      140.0"
"\n                 400       3.04      160.0"
"\n                 450       2.70      180.0"
"\n                 500       2.43      200.0"
"\n LIGHT <END> ^See the Top========================================="
)
)
) ;defun/light end
;;-------------------------------------------------------------------
(defun DIESPRING3-MEDIUM () 
(princ
(strcat
"\n=================================================================="
"\n                      CORE SPRING  (MEDIUM)"
"\n=================================================================="
"\n  I.D     O.D      H       RATE        MAX.           MAX."
"\n (mm)    (mm)     (mm)   (kgf/mm)  DEFLECTION(mm)   LOAD(kg)" 
"\n <4X8>------------------------------------------------------------" 
"\n   4    8          10      4.34        3.2           14 (137.3N)"
"\n                   15      2.89        4.8"
"\n                   20      2.17        6.4"
"\n                   25      1.74        8.0"
"\n                   30      1.45        9.6"
"\n                   35      1.24       11.2"
"\n                   40      1.09       12.8"
"\n                   45      0.97       14.4"
"\n                   50      0.87       16.0"
"\n                   55      0.79       17.6"
"\n                   60      0.72       19.2"
"\n                   65      0.67       20.8"
"\n                   70      0.62       22.4"
"\n                   75      0.58       24.0"
"\n                   80      0.54       25.6"
"\n <5X10>----------------------------------------------------------"
"\n   5     10        20      3.13        6.4          20 (196.1N)"
"\n                   25      2.50        8.0"
"\n                   30      2.08        9.6"
"\n                   35      1.78       11.2"
"\n                   40      1.56       12.8"
"\n                   45      1.38       14.4"
"\n                   50      1.25       16.0"
"\n                   55      1.13       17.6"
"\n                   60      1.04       19.2"
"\n                   65      0.96       20.8"
"\n                   70      0.89       22.4"
"\n                   75      0.83       24.0"
"\n                   80      0.78       25.6"
"\n                   90      0.69       28.8"
"\n <6X12>----------------------------------------------------------"
"\n   6     12        20      4.53        6.4            29 (284N)"
"\n                   25      3.62        8.0"
"\n                   30      3.02        9.6"
"\n                   35      2.58       11.2"
"\n                   40      2.27       12.8"
"\n                   45      2.01       14.4"
"\n                   50      1.81       16.0"
"\n                   55      1.64       17.6"
"\n                   60      1.51       19.2"
"\n                   65      1.39       20.8"
"\n                   70      1.29       22.4"
"\n                   75      1.20       24.0"
"\n                   80      1.13       25.6"
"\n                   90      1.00       28.8"
"\n-----------------------------------------------------------------"
"\n MEDIUM  <MORE> -press any key- ^See the Top:"
);princ
);strcat
(grread)
(princ
(strcat 
"\n <7X14>----------------------------------------------------------"
"\n   7     14        25      4.87        8.0            39 (383N)"
"\n                   30      4.06        9.6"
"\n                   35      3.48       11.2"
"\n                   40      3.04       12.8"
"\n                   45      2.70       14.4"
"\n                   50      2.43       16.0"
"\n                   55      2.21       17.6"
"\n                   60      2.03       19.2"
"\n                   65      1.87       20.8"
"\n                   70      1.74       22.4"
"\n                   75      1.62       24.0"
"\n                   80      1.52       25.6"
"\n                   90      1.35       28.8"
"\n                  100      1.21       32.0"
"\n <8X16>---------------------------------------------------------"
"\n   8     16        25      6.39        8.0           51 (500N)"
"\n                   30      5.32        9.6"
"\n                   35      4.55       11.2"
"\n                   40      3.98       12.8"
"\n                   45      3.54       14.4"
"\n                   50      3.18       16.0"
"\n                   55      2.89       17.6"
"\n                   60      2.65       19.2"
"\n                   65      2.45       20.8"
"\n                   70      2.27       22.4"
"\n                   75      2.11       24.0"
"\n                   80      1.99       25.6"
"\n                   90      1.77       28.8"
"\n                  100      1.59       32.0"
"\n                  125      1.28       40.0"
"\n <9X18>--------------------------------------------------------"
"\n   9     18        25      8.12        8.0          65 (637N)"
"\n                   30      6.77        9.6"
"\n                   35      5.80       11.2"
"\n                   40      5.07       12.8"
"\n                   45      4.51       14.4"
"\n                   50      4.06       16.0"
"\n                   55      3.69       17.6"
"\n                   60      3.38       19.2"
"\n                   65      3.12       20.8"
"\n                   70      2.90       22.4"
"\n                   75      2.70       24.0"
"\n                   80      2.53       25.6"
"\n                   90      2.25       28.8"
"\n                  100      2.02       32.0"
"\n                  125      1.61       40.0"
"\n-----------------------------------------------------------------"
"\n MEDIUM  <MORE> -press any key- ^See the Top:"
);princ
);strcat
(grread)
(princ
(strcat 
"\n <10X20>-------------------------------------------------------"
"\n   10     20       25      10.0	  8.0          80 (785N)"
"\n                   30      8.33	  9.6"
"\n                   40      6.25	 12.8"
"\n                   35      7.14	 11.2"
"\n                   45      5.55	 14.4"
"\n                   50      5.00	 16.0"
"\n                   55      4.54	 17.6"
"\n                   60      4.16	 19.2"
"\n                   65      3.84	 20.8"
"\n                   70      3.57	 22.4"
"\n                   75      3.33	 24.0"
"\n                   80      3.12	 25.6"
"\n                   90      2.77	 28.8"
"\n                  100      2.50	 32.0"
"\n                  125      2.00	 40.0"
"\n                  150      1.67	 48.0"
"\n <11X22>-------------------------------------------------------"
"\n   11     22       25     12.13	  8.0          97 (951N)"
"\n                   30     10.10	  9.6"
"\n                   35      8.65	 11.2"
"\n                   40      7.57	 12.8"
"\n                   45      6.74	 14.4"
"\n                   50      6.06	 16.0"
"\n                   55      5.50	 17.6"
"\n                   60      5.05	 19.2"
"\n                   65      4.66	 20.8"
"\n                   70      4.33	 22.4"
"\n                   75      4.04	 24.0"
"\n                   80      3.78	 25.6"
"\n                   90      3.36	 28.8"
"\n                  100      3.03	 32.0"
"\n                  125      2.42	 40.0"
"\n                  150      2.01	 48.0"
"\n <12.5X25>------------------------------------------------------"
"\n    12.5    25     25     15.63	  8.0	     125 (1,226N)"
"\n                   30     13.02	  9.6"
"\n                   35     11.20	 11.2"
"\n                   40      9.76	 12.8"
"\n                   45      8.68	 14.4"
"\n                   50      7.81	 16.0"
"\n                   55      7.10	 17.6"
"\n                   60      6.51	 19.2"
"\n                   65      6.00	 20.8"
"\n                   70      5.58	 22.4"
"\n                   75      5.21	 24.0"
"\n                   80      4.88	 25.6"
"\n                   90      4.34	 28.8"
"\n                  100      3.90	 32.0"
"\n                  125      3.12	 40.0"
"\n                  150      2.60	 48.0"
"\n                  175      2.23	 56.0"
"\n                  200      1.94	 64.0"
"\n-----------------------------------------------------------------"
"\n MEDIUM  <MORE> -press any key- ^See the Top:"
);princ
);strcat
(grread)
(princ
(strcat 
"\n <13.5X27>-------------------------------------------------------"
"\n    13.5    27     25     18.25        8.0         146 (1,432N)"
"\n                   30     15.20        9.6"
"\n                   35     13.04       11.2"
"\n                   40     11.40       12.8"
"\n                   45     10.14       14.4"
"\n                   50      9.12       16.0"
"\n                   55      8.30       17.6"
"\n                   60      7.60       19.2"
"\n                   65      7.00       20.8"
"\n                   70      6.51       22.4"
"\n                   75      6.08       24.0"
"\n                   80      5.70       25.6"
"\n                   90      5.06       28.8"
"\n                  100      4.56       32.0"
"\n                  125      3.65       40.0"
"\n                  150      3.04       48.0"
"\n                  175      2.61       56.0"
"\n <15X30>--------------------------------------------------------"
"\n   15     30       25     22.50        8.0        180 (1,765N)"
"\n                   30     18.75        9.6"
"\n                   35     16.10       11.2"
"\n                   40     14.06       12.8"
"\n                   45     12.50       14.4"
"\n                   50     11.25       16.0"
"\n                   55     10.23       17.6"
"\n                   60      9.37       19.2"
"\n                   65      8.65       20.8"
"\n                   70      8.03       22.4"
"\n                   75      7.50       24.0"
"\n                   80      7.03       25.6"
"\n                   90      6.25       28.8"
"\n                  100      5.62       32.0"
"\n                  125      4.50       40.0"
"\n                  150      3.75       48.0"
"\n                  175      3.21       56.0"
"\n                  200      2.81       64.0"
"\n <17.5X35>-------------------------------------------------------"
"\n    17.5    35     40     19.14       12.8         245 (2,400N)"
"\n                   45     17.01       14.4"
"\n                   50     15.31       16.0"
"\n                   55     13.92       17.6"
"\n                   60     12.76       19.2"
"\n                   65     11.77       20.8"
"\n                   70     10.93       22.4"
"\n                   75     10.20       24.0"
"\n                   80      9.57       25.6"
"\n                   90      8.50       28.8"
"\n                  100      7.65       32.0"
"\n                  125      6.12       40.0"
"\n                  150      5.10       48.0"
"\n                  175      4.37       56.0"
"\n                  200      3.82       64.0"
"\n-----------------------------------------------------------------"
"\n MEDIUM  <MORE> -press any key- ^See the Top:"
);princ
);strcat
(grread)
(princ
(strcat 
"\n <20X40>--------------------------------------------------------"
"\n   20     40       40     25.02       12.8        320 (3,140N)"
"\n                   45     22.19       14.4"
"\n                   50     20.00       16.0"
"\n                   55     18.15       17.6"
"\n                   60     16.60       19.2"
"\n                   65     15.36       20.8"
"\n                   70     14.28       22.4"
"\n                   75     13.31       24.0"
"\n                   80     12.50       25.6"
"\n                   90     11.11       28.8"
"\n                  100     10.00       32.0"
"\n                  125      8.00       40.0"
"\n                  150      6.66       48.0"
"\n                  175      5.71       56.0"
"\n                  200      5.00       64.0"
"\n                  225      4.44       72.0"
"\n                  250      4.00       80.0"
"\n                  275      3.63       88.0"
"\n                  300      3.33       96.0"
"\n <25X50>--------------------------------------------------------"
"\n   25     50       50     31.25       16.0        500 (4,900N)"
"\n                   55     28.39       17.6"
"\n                   60     26.04       19.2"
"\n                   65     24.02       20.8"
"\n                   70     22.32       22.4"
"\n                   75     20.82       24.0"
"\n                   80     19.53       25.6"
"\n                   90     17.36       28.8"
"\n                  100     15.62       32.0"
"\n                  125     12.50       40.0"
"\n                  150     10.41       48.0"
"\n                  175      8.92       56.0"
"\n                  200      7.81       64.0"
"\n                  225      6.94       72.0"
"\n                  250      6.25       80.0"
"\n                  275      5.68       88.0"
"\n                  300      5.20       96.0"
"\n                  350      4.46      112.0"
"\n MEDIUM <END> ^See the Top======================================="
)
)
);defun/medium end
;-------------------------------------------------------------------
(defun DIESPRING4-HEAVY () 
(princ
(strcat
"\n================================================================"
"\n                      CORE SPRING  (HEAVY)"
"\n================================================================"
"\n  I.D     O.D      H       RATE        MAX.           MAX."
"\n (mm)    (mm)     (mm)   (kgf/mm)  DEFLECTION(mm)   LOAD(kg)"
"\n <4X8>----------------------------------------------------------"
"\n   4    8         10       8.80        2.4         21.0 (206N)"
"\n                  15       5.86        3.6"
"\n                  20       4.40        4.8"
"\n                  25       3.52        6.0"
"\n                  30       2.93        7.2"
"\n                  35       2.51        8.4"
"\n                  40       2.20        9.6"
"\n                  45       1.95       10.8"
"\n                  50       1.76       12.0"
"\n                  55       1.60       13.2"
"\n                  60       1.47       14.4"
"\n                  65       1.35       15.6"
"\n                  70       1.26       16.8"
"\n                  75       1.17       18.0"
"\n                  80       1.10       19.2"
"\n <5X10>---------------------------------------------------------"
"\n   5     10       20       6.25        4.8           30 (294N)"
"\n                  25       5.00        6.0"
"\n                  30       4.16        7.2"
"\n                  35       3.57        8.4"
"\n                  40       3.15        9.6"
"\n                  45       2.77       10.8"
"\n                  50       2.50       12.0"
"\n                  55       2.27       13.2"
"\n                  60       2.08       14.4"
"\n                  65       1.92       15.6"
"\n                  70       1.79       16.8"
"\n                  75       1.67       18.0"
"\n                  80       1.56       19.2"
"\n                  90       1.39       21.6"
"\n <6X12>---------------------------------------------------------"
"\n   6     12       20       8.90        4.8           43 (422N)"
"\n                  25       7.10        6.0"
"\n                  30       5.97        7.2"
"\n                  35       5.11        8.4"
"\n                  40       4.47        9.6"
"\n                  45       3.98       10.8"
"\n                  50       3.58       12.0"
"\n                  55       3.25       13.2"
"\n                  60       2.98       14.4"
"\n                  65       2.74       15.6"
"\n                  70       2.54       16.8"
"\n                  75       2.37       18.0"
"\n                  80       2.21       19.2"
"\n                  90       1.96       21.6"
"\n----------------------------------------------------------------"
"\n HEAVY  <MORE> -press any key- ^See the Top:"
);princ
);strcat
(grread)
(princ
(strcat 
"\n <7X14>---------------------------------------------------------"
"\n   7     14       25       9.83        6.0           59 (579N)"
"\n                  30       8.19        7.2"
"\n                  35       7.02        8.4"
"\n                  40       6.14        9.6"
"\n                  45       5.46       10.8"
"\n                  50       4.91       12.0"
"\n                  55       4.46       13.2"
"\n                  60       4.09       14.4"
"\n                  65       3.78       15.6"
"\n                  70       3.51       16.8"
"\n                  75       3.27       18.0"
"\n                  80       3.07       19.2"
"\n                  90       2.72       21.6"
"\n                 100       2.45       24.0"
"\n <8X16>---------------------------------------------------------"
"\n   8     16       25      12.83        6.0           77 (755N)"
"\n                  30      10.69        7.2"
"\n                  35       9.16        8.4"
"\n                  40       8.02        9.6"
"\n                  45       7.12       10.8"
"\n                  50       6.41       12.0"
"\n                  55       5.83       13.2"
"\n                  60       5.34       14.4"
"\n                  65       4.93       15.6"
"\n                  70       4.58       16.8"
"\n                  75       4.28       18.0"
"\n                  80       4.01       19.2"
"\n                  90       3.57       21.6"
"\n                 100       3.21       24.0"
"\n                 125       2.56       30.0"
"\n <9X18>--------------------------------------------------------"
"\n   9     18       25      16.16        6.0          97 (951N)"
"\n                  30      13.47        7.2"
"\n                  35      11.54        8.4"
"\n                  40      10.10        9.6"
"\n                  45       8.98       10.8"
"\n                  50       8.08       12.0"
"\n                  55       7.34       13.2"
"\n                  60       6.73       14.4"
"\n                  65       6.21       15.6"
"\n                  70       5.77       16.8"
"\n                  75       5.39       18.0"
"\n                  80       5.05       19.2"
"\n                  90       4.50       21.6"
"\n                 100       4.04       24.0"
"\n                 125       3.22       30.0"
"\n----------------------------------------------------------------"
"\n HEAVY  <MORE> -press any key- ^See the Top:"
);princ
);strcat
(grread)
(princ
(strcat 
"\n <10X20>---------------------------------------------------------"
"\n   10     20      25      20.00        6.0         120 (1,177N)"
"\n                  30      16.66        7.2"
"\n                  35      14.28        8.4"
"\n                  40      12.50        9.6"
"\n                  45      11.11       10.8"
"\n                  50      10.00       12.0"
"\n                  55       9.09       13.2"
"\n                  60       8.33       14.4"
"\n                  65       7.69       15.6"
"\n                  70       7.14       16.8"
"\n                  75       6.67       18.0"
"\n                  80       6.25       19.2"
"\n                  90       5.55       21.6"
"\n                 100       5.00       24.0"
"\n                 125       4.00       30.0"
"\n                 150       3.33       36.0"
"\n <11X22>--------------------------------------------------------"
"\n   11     22      25      24.16        6.0        145 (1,422N)"
"\n                  30      20.13        7.2"
"\n                  35      17.30        8.4"
"\n                  40      15.10        9.6"
"\n                  45      13.40       10.8"
"\n                  50      12.08       12.0"
"\n                  55      10.94       13.2"
"\n                  60      10.06       14.4"
"\n                  65       9.28       15.6"
"\n                  70       8.63       16.8"
"\n                  75       8.04       18.0"
"\n                  80       7.55       19.2"
"\n                  90       6.71       21.6"
"\n                 100       6.04       24.0"
"\n                 125       4.83       30.0"
"\n                 150       4.02       36.0"
"\n <12.5X25>-------------------------------------------------------"
"\n   12.5     25    25      31.20        6.0         187 (1,834N)"
"\n                  30      25.97        7.2"
"\n                  35      22.38        8.4"
"\n                  40      19.47        9.6"
"\n                  45      17.40       10.8"
"\n                  50      15.58       12.0"
"\n                  55      14.20       13.2"
"\n                  60      12.98       14.4"
"\n                  65      12.00       15.6"
"\n                  70      11.13       16.8"
"\n                  75      10.40       18.0"
"\n                  80       9.73       19.2"
"\n                  90       8.65       21.6"
"\n                 100       7.79       24.0"
"\n                 125       6.23       30.0"
"\n                 150       5.20       36.0"
"\n                 175       4.46       42.0"
"\n                 200       3.91       48.0"
"\n-----------------------------------------------------------------"
"\n HEAVY  <MORE> -press any key- ^See the Top:"
);princ
);strcat
(grread)
(princ
(strcat 
"\n <13.5X27>-------------------------------------------------------"
"\n   13.5     27    25      36.40        6.0         219 (2,150N)"
"\n                  30      30.41        7.2"
"\n                  35      26.20        8.4"
"\n                  40      22.81        9.6"
"\n                  45      20.30       10.8"
"\n                  50      18.25       12.0"
"\n                  55      16.50       13.2"
"\n                  60      15.20       14.4"
"\n                  65      14.00       15.6"
"\n                  70      13.03       16.8"
"\n                  75      12.10       18.0"
"\n                  80      11.40       19.2"
"\n                  90      10.13       21.6"
"\n                 100       9.12       24.0"
"\n                 125       7.30       30.0"
"\n                 150       6.08       36.0"
"\n                 175       5.21       42.0"
"\n                 200       4.56       48.0"
"\n <15X30>---------------------------------------------------------"
"\n   15     30      25      45.00        6.0         270 (2,550N)"
"\n                  30      37.50        7.2"
"\n                  35      32.26        8.4"
"\n                  40      28.12        9.6"
"\n                  45      25.00       10.8"
"\n                  50      22.50       12.0"
"\n                  55      20.40       13.2"
"\n                  60      18.75       14.4"
"\n                  65      17.30       15.6"
"\n                  70      16.07       16.8"
"\n                  75      15.00       18.0"
"\n                  80      14.06       19.2"
"\n                  90      12.50       21.6"
"\n                 100      11.25       24.0"
"\n                 125       9.00       30.0"
"\n                 150       7.50       36.0"
"\n                 175       6.42       42.0"
"\n                 200       5.62       48.0"
"\n <17.5X35>------------------------------------------------------"
"\n   17.5     35    40      38.22        9.6          367(3,600)"
"\n                  45      33.98       10.8"
"\n                  50      30.58       12.0"
"\n                  55      27.80       13.2"
"\n                  60      25.48       14.4"
"\n                  65      23.53       15.6"
"\n                  70      21.84       16.8"
"\n                  75      20.39       18.0"
"\n                  80      19.11       19.2"
"\n                  90      16.99       21.6"
"\n                 100      15.29       24.0"
"\n                 125      12.23       30.0"
"\n                 150      10.19       36.0"
"\n                 175       8.73       42.0"
"\n                 200       7.64       48.0"
"\n-----------------------------------------------------------------"
"\n HEAVY  <MORE> -press any key- ^See the Top:"
);princ
);strcat
(grread)
(princ
(strcat 
"\n <20X40>---------------------------------------------------------"
"\n   20     40      40      50.00        9.6         480 (4,710N)"
"\n                  45      44.48       10.8"
"\n                  50      40.00       12.0"
"\n                  55      36.39       13.2"
"\n                  60      33.33       14.4"
"\n                  65      30.79       15.6"
"\n                  70      28.57       16.8"
"\n                  75      26.69       18.0"
"\n                  80      25.00       19.2"
"\n                  90      22.22       21.6"
"\n                 100      20.00       24.0"
"\n                 125      16.00       30.0"
"\n                 150      13.33       36.0"
"\n                 175      11.42       42.0"
"\n                 200      10.00       48.0"
"\n                 225       8.90       54.0"
"\n                 250       8.00       60.0"
"\n                 275       7.28       66.0"
"\n                 300       6.67       72.0"
"\n <25X50>---------------------------------------------------------"
"\n   25     50      50      62.50       12.0         750 (7,360N)"
"\n                  55      56.82       13.2"
"\n                  60      52.08       14.4"
"\n                  65      48.08       15.6"
"\n                  70      44.64       16.8"
"\n                  75      41.67       18.0"
"\n                  80      39.06       19.2"
"\n                  90      34.72       21.6"
"\n                 100      31.25       24.0"
"\n                 125      25.00       30.0"
"\n                 150      20.83       36.0"
"\n                 175      17.85       42.0"
"\n                 200      15.62       48.0"
"\n                 225      13.89       54.0"
"\n                 250      12.50       60.0"
"\n                 275      11.36       66.0"
"\n                 300      10.41       72.0"
"\n                 350       8.93       84.0"
"\n <30X60>----------------------------------------------------------"
"\n   30     60      60      75.00       14.4       1,080 (10,590N)"
"\n                  70      64.28       16.8"
"\n                  80      56.25       19.2"
"\n                  90      50.00       21.6"
"\n                 100      45.00       24.0"
"\n                 125      36.00       30.0"
"\n                 150      30.00       36.0"
"\n                 175      25.71       42.0"
"\n                 200      22.50       48.0"
"\n                 225      20.02       54.0"
"\n                 250      18.00       60.0"
"\n                 275      16.38       66.0"
"\n                 300      15.00       72.0"
"\n                 350      12.87       84.0"
"\n HEAVY <END> ^See the Top=========================================="
)
)
);defun/heavy end
;---------------------------------------------------------------------
(defun DIESPRING5-EXTRAHEAVY () 
(princ
(strcat
"\n================================================================="
"\n                      CORE SPRING  (EXTRA HEAVY)"
"\n================================================================="
"\n  I.D     O.D      H       RATE        MAX.           MAX."
"\n (mm)    (mm)     (mm)   (kgf/mm)  DEFLECTION(mm)   LOAD(kg)"
"\n <4X8>-----------------------------------------------------------"
"\n   4    8         10       16.94       2.0          35.0 (343N)"
"\n                  15       11.30       3.0"
"\n                  20        8.47       4.0"
"\n                  25        6.78       5.0"
"\n                  30        5.65       6.0"
"\n                  35        4.84       7.0"
"\n                  40        4.20       8.0"
"\n                  45        3.77       9.0"
"\n                  50        3.39      10.0"
"\n                  55        3.08      11.0"
"\n                  60        2.82      12.0"
"\n                  65        2.61      13.0"
"\n                  70        2.42      14.0"
"\n                  75        2.26      15.0"
"\n                  80        2.12      16.0"
"\n <5X10>----------------------------------------------------------"
"\n   5     10       20       11.25       4.0          45.0 (441N)"
"\n                  25        9.00       5.0"
"\n                  30        7.50       6.0"
"\n                  35        6.43       7.0"
"\n                  40        5.63       8.0"
"\n                  45        5.00       9.0"
"\n                  50        4.50      10.0"
"\n                  55        4.09      11.0"
"\n                  60        3.75      12.0"
"\n                  65        3.47      13.0"
"\n                  70        3.21      14.0"
"\n                  75        3.00      15.0"
"\n                  80        2.82      16.0"
"\n                  90        2.53      18.0"
"\n <6X12>----------------------------------------------------------"
"\n   6     12       20       14.50       4.0          58.0 (569N)"
"\n                  25       11.60       5.0"
"\n                  30        9.67       6.0"
"\n                  35        8.29       7.0"
"\n                  40        7.25       8.0"
"\n                  45        6.44       9.0"
"\n                  50        5.80      10.0"
"\n                  55        5.27      11.0"
"\n                  60        4.83      12.0"
"\n                  65        4.44      13.0"
"\n                  70        4.13      14.0"
"\n                  75        3.85      15.0"
"\n                  80        3.61      16.0"
"\n-----------------------------------------------------------------"
"\n EXTRA HEAVY <MORE> -press any key- ^See the Top:"
);princ
);strcat
(grread)
(princ
(strcat
"\n <7X14>----------------------------------------------------------"
"\n   7     14       25       15.00       5.0          75.0 (736N)"
"\n                  30       12.50       6.0"
"\n                  35       10.72       7.0"
"\n                  40        9.38       8.0"
"\n                  45        8.34       9.0"
"\n                  50        7.50      10.0"
"\n                  55        6.82      11.0"
"\n                  60        6.25      12.0"
"\n                  65        5.77      13.0"
"\n                  70        5.36      14.0"
"\n                  75        5.00      15.0"
"\n                  80        4.69      16.0"
"\n                  90        4.17      18.0"
"\n                 100        3.78      20.0"
"\n <8X16>---------------------------------------------------------"
"\n   8     16       25       20.00       5.0          100 (981N)"
"\n                  30       16.67       6.0"
"\n                  35       14.29       7.0"
"\n                  40       12.50       8.0"
"\n                  45       11.11       9.0"
"\n                  50       10.00      10.0"
"\n                  55        9.09      11.0"
"\n                  60        8.34      12.0"
"\n                  65        7.69      13.0"
"\n                  70        7.14      14.0"
"\n                  75        6.67      15.0"
"\n                  80        6.25      16.0"
"\n                  90        5.56      18.0"
"\n                 100        5.00      20.0"
"\n                 125        4.00      25.0"
"\n <9X18>----------------------------------------------------------"
"\n   9     18       25       25.00       5.0          125 (1,226N)"
"\n                  30       20.84       6.0"
"\n                  35       17.86       7.0"
"\n                  40       15.63       8.0"
"\n                  45       13.89       9.0"
"\n                  50       12.50      10.0"
"\n                  55       11.37      11.0"
"\n                  60       10.42      12.0"
"\n                  65        9.62      13.0"
"\n                  70        8.93      14.0"
"\n                  75        8.34      15.0"
"\n                  80        7.82      16.0"
"\n                  90        6.95      18.0"
"\n                 100        6.26      20.0"
"\n                 125        5.02      25.0"
"\n-----------------------------------------------------------------"
"\n EXTRA HEAVY  <MORE> -press any key- ^See the Top:"
);princ
);strcat
(grread)
(princ
(strcat
"\n <10X20>---------------------------------------------------------"
"\n   10     20      25       32.00       5.0         160 (1,569N)"
"\n                  30       26.67       6.0"
"\n                  35       22.86       7.0"
"\n                  40       20.00       8.0"
"\n                  45       17.78       9.0"
"\n                  50       16.00      10.0"
"\n                  55       14.55      11.0"
"\n                  60       13.33      12.0"
"\n                  65       12.31      13.0"
"\n                  70       11.43      14.0"
"\n                  75       10.67      15.0"
"\n                  80       10.00      16.0"
"\n                  90        8.89      18.0"
"\n                 100        8.00      20.0"
"\n                 125        6.40      25.0"
"\n                 150        5.33      30.0"
"\n <11X22>----------------------------------------------------------"
"\n   11     22      25       39.00       5.0          195 (1,912N)"
"\n                  30       32.50       6.0"
"\n                  35       27.86       7.0"
"\n                  40       24.38       8.0"
"\n                  45       21.67       9.0"
"\n                  50       19.50      10.0"
"\n                  55       17.73      11.0"
"\n                  60       16.25      12.0"
"\n                  65       15.00      13.0"
"\n                  70       13.93      14.0"
"\n                  75       13.00	 15.0"
"\n                  80       12.19      16.0"
"\n                  90       10.83      18.0"
"\n                 100        9.75      20.0"
"\n                 125        7.80      25.0"
"\n                 150        6.50      30.0"
"\n <12.5X25>---------------------------------------------------------"
"\n   12.5     25    25       49.00       5.0           245 (2,400N)"
"\n                  30       40.80       6.0"
"\n                  35       35.00       7.0"
"\n                  40       30.60       8.0"
"\n                  45       27.20       9.0"
"\n                  50       24.50      10.0"
"\n                  55       22.30      11.0"
"\n                  60       20.40      12.0"
"\n                  65       18.80      13.0"
"\n                  70       17.50      14.0"
"\n                  75       16.30      15.0"
"\n                  80       15.30      16.0"
"\n                  90       13.60      18.0"
"\n                 100       12.30      20.0"
"\n                 125        9.80      25.0"
"\n                 150        8.17      30.0"
"\n                 175        7.00      35.0"
"\n                 200        6.15      40.0"
"\n------------------------------------------------------------------"
"\n EXTRA HEAVY  <MORE> -press any key- ^See the Top:"
);princ
);strcat
(grread)
(princ
(strcat
"\n <13.5X27>--------------------------------------------------------" 
"\n    13.5    27    25      58.00        5.0          290 (2,840N)"
"\n                  30      48.33        6.0"
"\n                  35      41.43        7.0"
"\n                  40      36.25        8.0"
"\n                  45      32.22        9.0"
"\n                  50      29.00       10.0"
"\n                  55      26.36       11.0"
"\n                  60      24.17       12.0"
"\n                  65      22.31       13.0"
"\n                  70      20.71       14.0"
"\n                  75      19.33       15.0"
"\n                  80      18.13       16.0"
"\n                  90      16.11       18.0"
"\n                 100      14.50       20.0"
"\n                 125      11.60       25.0"
"\n                 150       9.67       30.0"
"\n                 175       8.28       35.0"
"\n                 200       7.25       40.0"
"\n <15X30>----------------------------------------------------------"
"\n   15     30      25      72.00        5.0          360 (3,530N)"
"\n                  30      60.00        6.0"
"\n                  35      51.43        7.0"
"\n                  40      45.00        8.0"
"\n                  45      40.00        9.0"
"\n                  50      36.00       10.0"
"\n                  55      32.72       11.0"
"\n                  60      30.00       12.0"
"\n                  65      27.69       13.0"
"\n                  70      25.71       14.0"
"\n                  75      24.00       15.0"
"\n                  80      22.50       16.0"
"\n                  90      20.00       18.0"
"\n                 100      18.00       20.0"
"\n                 125      14.40       25.0"
"\n                 150      12.00       30.0"
"\n                 175      10.28       35.0"
"\n                 200       9.00       40.0"
"\n <17.5X35>---------------------------------------------------------"
"\n    17.5    35    40      61.20        8.0           490 (4,810N)"
"\n                  45      54.44        9.0"
"\n                  50      49.00       10.0"
"\n                  55      44.54       11.0"
"\n                  60      40.83       12.0"
"\n                  65      37.69       13.0"
"\n                  70      35.00       14.0"
"\n                  75      32.67       15.0"
"\n                  80      30.62       16.0"
"\n                  90      27.22       18.0"
"\n                 100      24.50       20.0"
"\n                 125      19.60       25.0"
"\n                 150      16.33       30.0"
"\n                 175      14.00       35.0"
"\n                 200      12.25       40.0"
"\n------------------------------------------------------------------"
"\n EXTRA HEAVY  <MORE> -press any key- ^See the Top:"
);princ
);strcat
(grread)
(princ
(strcat
"\n <20X40>----------------------------------------------------------"
"\n   20     40      40      80.00        8.0          640 (6,280N)"
"\n                  45      71.13        9.0"
"\n                  50      64.00       10.0"
"\n                  55      58.20       11.0"
"\n                  60      53.33       12.0"
"\n                  65      49.24       13.0"
"\n                  70      45.71       14.0"
"\n                  75      42.68       15.0"
"\n                  80      40.00       16.0"
"\n                  90      35.55       18.0"
"\n                 100      32.00       20.0"
"\n                 125      25.60       25.0"
"\n                 150      21.33       30.0"
"\n                 175      18.28       35.0"
"\n                 200      16.00       40.0"
"\n                 225      14.23       45.0"
"\n                 250      12.80       50.0"
"\n                 275      11.64       55.0"
"\n                 300      10.67       60.0"
"\n <25X50>-----------------------------------------------------------"
"\n   25     50      50      100.0       10.0         1,000 (9,810N)"
"\n                  55      90.95       11.0"
"\n                  60      83.33       12.0"
"\n                  65      76.96       13.0"
"\n                  70      71.42       14.0"
"\n                  75      66.70       15.0"
"\n                  80      62.50       16.0"
"\n                  90      55.55       18.0"
"\n                 100      50.00       20.0"
"\n                 125      40.00       25.0"
"\n                 150      33.33       30.0"
"\n                 175      28.57       35.0"
"\n                 200      25.00       40.0"
"\n                 225      22.23       45.0"
"\n                 250      20.00       50.0"
"\n                 275      18.19       55.0"
"\n                 300      16.66       60.0"
"\n                 350      14.29       70.0"
"\n EXTRA HEAVY <END> ^See the Top===================================="
)
)
);defun/super heavy
;---------------------------------------------------------------------
(defun menu-1 () ;스프링강(SPS/SUP)
(progn
(setq dw (getreal "\n선경 (mm): "))
(if	(= m 1)	
(progn
(setq g 8000) ;g=횡탄성계수(kg/mm2)/tsl=인장강도(kg/mm2)
(setq tsl 125)
(setq matl "스프링강(SPS/SUP)")
)
)
;----------------------------------
(if	(= m 5)	;인청동선(C5191-WH)
(progn
(setq g 4300)
(setq matl "인청동선(C5191-WH)")
(cond
((and (> dw 0.63) (<= dw 5.0)) (setq tsl 85))
((> dw 5.0) (princ "\n선경 5mm이상 없음") (menu-1))
((< dw 0.63) (princ "\n선경 0.63mm이하 없음") (menu-1))
)
)
)
;---------------------------
(if	(= m 2)	;경강선(SWB)
(progn
(setq g 8000)
(setq matl "경강선(SWB)")
(cond
((<= dw 0.5) (setq tsl 195))
((and (> dw 0.5) (<= dw 1.0)) (setq tsl 175))
((and (> dw 1.0) (<= dw 2.0)) (setq tsl 150))
((and (> dw 2.0) (<= dw 4.0)) (setq tsl 140))
((and (> dw 4.0) (<= dw 5.0)) (setq tsl 135))
((and (> dw 5.0) (<= dw 6.0)) (setq tsl 125))
((and (> dw 6.0) (<= dw 8.0)) (setq tsl 120))
((and (> dw 8.0) (<= dw 10.0)) (setq tsl 115))
((and (> dw 10.0) (<= dw 12.0)) (setq tsl 110))
((and (> dw 12.0) (<= dw 13.0)) (setq tsl 105))
((> dw 13.0) (princ "\n선경 13mm이상 없음") (menu-1))
)
)
);if 경강선(SWB)
;-------------------------------
(if	(= m 3)	;피아노선(SWP-A)
(progn
(setq g 8000)
(setq matl "피아노선(SWP-A)")
(cond
((<= dw 0.5) (setq tsl 230))
((and (> dw 0.5) (<= dw 1.0)) (setq tsl 210))
((and (> dw 1.0) (<= dw 2.0)) (setq tsl 185))
((and (> dw 2.0) (<= dw 4.0)) (setq tsl 170))
((and (> dw 4.0) (<= dw 5.0)) (setq tsl 165))
((and (> dw 5.0) (<= dw 6.0)) (setq tsl 155))
((and (> dw 6.0) (<= dw 8.0)) (setq tsl 150))
((and (> dw 8.0) (<= dw 10.0)) (setq tsl 145))
((> dw 10.0) (princ "\n선경 10mm이상 없음") (menu-1))
)
)
);피아노선(SWP-A)
;---------------------------------------
(if	(= m 4)	;스테인레스선(STS304WPRA)
(progn
(setq g 7200)
(setq matl "스테인레스선(STS304WPRA)")
(cond
((<= dw 0.2) (setq tsl 220))
((and (> dw 0.2) (<= dw 0.4)) (setq tsl 210))
((and (> dw 0.4) (<= dw 0.7)) (setq tsl 200))
((and (> dw 0.7) (<= dw 1.0)) (setq tsl 190))
((and (> dw 1.0) (<= dw 1.4)) (setq tsl 180))
((and (> dw 1.4) (<= dw 2.0)) (setq tsl 170))
((and (> dw 2.0) (<= dw 2.6)) (setq tsl 160))
((and (> dw 2.6) (<= dw 4.0)) (setq tsl 150))
((and (> dw 4.0) (<= dw 5.0)) (setq tsl 140))
((> dw 5.0) (princ "\n선경 5mm/NONE") (menu-1))
)
)
);if/스테인레스선(STS304WPRA)
)
);defun menu1
;----------------------------
(defun menu-2 ()
(progn
(princ "\n<<중심경=(선경x4)~(선경x22) 범위내>>")
(setq an1 (strcase (getstring "\n<India./Outdia./Pcd> : ")))
(if	(= an1 "")
(exit)
)
(if	(= an1 "I")
(progn
(setq di (getreal "\nindia (mm): "))
(setq d (+ di dw))		;평균경
(setq do (+ di (* dw 2.0)))
)
)
(if	(= an1 "O")
(progn
(setq do (getreal "\noutdia (mm): "))
(setq d (- do dw))		;평균경
(setq di (- do (* dw 2.0)))
)
)
(if	(= an1 "P")
(progn
(setq dp (getreal "\npcd (mm): "))
(setq d dp)			;평균경
(setq di (- dp dw))
(setq do (+ dp dw))
)
)
;
(setq c (/ d dw))	;스프링지수(4~22)
(if	(and (> c 4.0) (< c 22.0))
(setq txt "OK!")
(setq txt "BAD!")
)
;
(cond
((< c 4.0)
(princ (strcat "\nREDUCE WIRE DIA.! 스프링지수(4~22):<"
      (rtos c 2 2)
      ">"
)
)
(menu-1)
)
((> c 22.0)
(princ (strcat "\n선경을 늘임! 스프링지수(4~22):<"
      (rtos c 2 2)
      ">"
)
)
(menu-1)
)
)
)
);defun menu2 
;-----------------------------------------------------------------------------------
(defun c:spring	(/   ans  m    matl g	 dw   an1  d	di   do   c    p    na	  hf
 pt   osm  ocmde     tbl  jb   ts   de	 k    so   s	nt   x	  hc   tn   ct    gak
 hd   hp   u	hf1  q	  tsl  ef   pch	 fl   hdr  msg1	msg2 na1  hs   th   vt    ht
 pn   ti   tbl	an1  po	  p1   p2   p3	 p4   p5   p6	ef1  p7	  p8   et   sp1   sp
 p9   p9a  p10	p11  p12  p13  p14  p15	 p16  p17  p18	p19  r	  p20  ar   ent   l1
 e1   e2   e3	e4   e5	  e6   e7   e8	 e9   e10  e11	e12  e13  e14  l2   ang1  ang
 e15  e16  e17	e18  e19  e20  e2l  e22	 e23  e24  k	hs   hk	  c1   ent1 lp  
 c2   c3   c4	i1   i2	  i3   i4   txt	 k1   h	   h1	w1   w	  pk
 p21  p22  p23	p24  de1  h    l    po1	 p21  p22  p23	p24  p25  p26
 p27  p28  p29	p30  p31  p32  p33  p34	 p35  p36  e24	e25  e26  e27
 e28  e29  c5	c6   e30  p23-1	    hfo	 od   id   an   sd   st   fd)
(command "undo" "be")
(setq	olderr	*error* *error*	spring_er)
(setq osm (getvar "osmode"))
(setq ocmde (getvar "cmdecho"))
(setvar "cmdecho" 0)
(setq tbl (tblsearch "LAYER" "cen-m"))
(if (= tbl nil)
(command "layer" "n" "cen-m" "c" 6 "cen-m" "lt" "center2" "cen-m" "")
)
(textpage)
;--------------------------------------------------------------
(princ "\n--------------------------------------------------------")
(princ "\n 1.압축스프링      2.기존 압축스프링     3.인장스프링")
(princ "\n 4.CORE(DIE) 스프링LIST(1)   5.CORE(DIE) 스프링 LIST(2)")
(princ "\n 6.CORE(DIE) 스프링 DRAW (기존,현품)")
(princ "\n--------------------------------------------------------")
(setq ans (getstring "\nSelect No: "))
(if (= ans "")
(exit)
)
;
(if (= ans "1")	;압축스프링
(progn
(princ
(strcat
"\n※Condition: 양끝연삭 압축스프링 / 선경에 따른 인장강도는 평균및 최소기준"
"\n※ 1항: 스프링강[SPS,SUP(JIS기호)]-판스프링및코일스프링용,열간성형,중대형"
"\n 2~5항: 냉간성형용"
"\n---------------------------------------------------------------------------"
"\n1.스프링강(SPS/SUP)          2.경강선(SWB,HSW)    3.피아노선(SWP-A,PW1)"
"\n4.스테인레스선(STS304WPRA)   5.인청동선(C5191-WH)"
"\n---------------------------------------------------------------------------")
)
(setq m (getint "\n재질/select no. <3>: "))
(if (= m nil)
(setq m 3)
)
(menu-1)
(menu-2)
(setq p (getreal "\n부하하중 (kg): "))
(setq na (getint "\n 유효권수>3 (정수): "))
(setq de (/ (* 8 na (expt d 3) p) (* g (expt dw 4)))) ;deflection(mm)
(setq nt (+ na 1.5))		;총권수
(setq hc (+ (* (- nt 1.0) dw) (/ dw 3.0))) ;밀착높이(mm)
(setq q (+ de hc))		;휨길이+압축길이
(princ (strcat "\n자유높이: (" (rtos (+ q 4) 2 2) "이상)"))
(setq hf (getreal "\n자유높이 (mm): "))
(setq pt (/ (- hf (/ dw 2)) na));계산pitch(0.5d이하)
(setq pch (* 0.5 d))		;pitch(0.5d이하)
(if (> pt pch)
(progn
(princ "\n선경을 늘림! ")
(menu-1)
(setq pt (/ (- hf (/ dw 2)) na)) ;pitch
)
)
(setq jb (/ hf d)) ;종횡비
(if (or (< jb 0.8) (> jb 4))
(progn
(princ (strcat "\n자유높이 수정! <종횡비:"
	 (rtos jb 2 2)
	 ">"
	 " ("
	 (rtos (+ q 4) 2 2)
	 "이상)"
 )
)
(setq hf (getreal "\n자유높이 (mm): "))
(setq jb (/ hf d)) ;종횡비
)
)
(if (and (> jb 0.8) (< jb 4.0))
(setq txt "OK")
(setq txt "BAD")
)
(if (< pt pch)
(setq txt "-OK!")
(setq txt "-BAD!")
)
;-------------------------------------------------------------------------
(setq h1 (+ (/ pt 2.0) (* pt (- na 1))))
(setq h (/ (- hf h1) 2.0))
(setq hc (+ (* dw na) (- h (/ dw 2.0)) (/ dw 2.0)))       ;실압축길이
(setq ts (+ (/ (- (* 4 c) 1) (- (* 4 c) 4)) (/ 0.615 c))) ;응력수정계수
(setq k (/ (* g (expt dw 4.0)) (* 8.0 na (expt d 3.0))))  ;스프링상수(kg/mm)
(setq so (/ (* 8 d p) (* pi (expt dw 3)))) ;비틀림응력(kg/mm2)
(setq s (* ts so))		;수정비틀림응력(kg/mm2)  
(setq hd (- hf de))		;부하하중시 총높이(mm)
(setq hdr (* (/ hd hf) 100))	;부하하중시 비율(%)
(setq hp (* (/ hd hf) 100))	;%
(setq u (/ (* p de) 2))		;축적에너지(kg.mm)
(setq ef (/ tsl s))		;안전율
(if (>= ef 2.5)
(setq txt "OK!")
(setq txt "BAD!")
)
;DRAW--------------------------------------------------
(setq an1 (strcase (getstring "\nDRAW ? <Y/N> <Y>: ")))
(if (= an1 "N")
(exit)
)
(if (or (= an1 "") (= an1 "Y"))
(progn
(setq w1 (* (- h (/ dw 2.0)) (- dw (- h (/ dw 2.0)))))
(setq w (* 2.0 (sqrt w1)))
;
(graphscr)
(setq po (getpoint "\ninsertion point of bottom center "))
(setq	p1  (polar po (dtr 0.0) (/ d 2.0))
p2  (polar p1 (dtr 0.0) (/ dw 2.0))
p3  (polar p1 (dtr 90.0) (/ dw 2.0))
p4  (polar p1 (dtr 180.0) (/ dw 2.0))
p5  (polar p1 (dtr 180.0) d)
p6  (polar p5 (dtr 0.0) (/ w 2.0))
p7  (polar p6 (dtr 180.0) w)
p8  (polar p5 (dtr 90.0) (- h (/ dw 2.0)))
p9  (polar p5 (dtr 90.0) h)
p9a (polar p9 (dtr 0.0) d)
p10 (polar p9 (dtr 90.0) (/ w 2.0))
p11 (polar p9a (dtr 90.0) (/ pt 2.0))
p12 (polar p11 (dtr 270.0) (/ dw 2.0))
p13 (polar p11 (dtr 90.0) (/ dw 2.0))
p14 (polar p9 (dtr 90.0) pt)
p15 (polar p14 (dtr 270.0) (/ dw 2.0))
p16 (polar p14 (dtr 90.0) (/ dw 2.0))
p17 (polar p11 (dtr 90.0) pt)
p18 (polar p17 (dtr 270.0) (/ dw 2.0))
p19 (polar p5 (dtr 90.0) hf)
p20 (polar p8 (dtr 270.0) (/ dw 2.0))
p21 (polar p1 (dtr 120.0) (+ 0.1 (/ dw 2.0)))
p22 (polar p5 (dtr 60.0) (+ 0.1 (/ dw 2.0)))
p23 (polar po (dtr 270.0) (/ dw 2.0))       ;center
p24 (polar po (dtr 90.0) (+ hf (/ dw 2.0))) ;center
pk  (polar po (dtr 90.0) hf)
c1  (polar p5 (dtr 270.0) (/ dw 2.0)) ;c1~c4 선경의 center line
c2  (polar p5 (dtr 90.0) (+ hf (/ dw 2.0)))
c3  (polar c1 (dtr 0.0) d)
c4  (polar p1 (dtr 90.0) (+ hf (/ dw 2.0)))
)
;
(setvar "osmode" 0)
(command "arc" "c" p1 p2 p4)
(setq e1 (entlast))
(command "arc" "c" p20 p6 p7)
(setq e2 (entlast))
(command "circle" p9 "d" dw)
(setq e3 (entlast))
(command "circle" p11 "d" dw)
(setq e4 (entlast))
(command "circle" p14 "d" dw)
(setq e5 (entlast))		;del.
(command "circle" p17 "d" dw)
(setq e6 (entlast))		;del.
;
(command "line" "_end" p7 "_end" p2 "")
(setq e7 (entlast))
(command "line" "_tan" p8 "_tan" p3 "")
(setq e8 (entlast))
(command "line" "_tan" p3 "_tan" p10 "")
(setq e9 (entlast))		;del.
;
(command "line" "_tan" p8 "_tan" p12 "")
(setq e10 (entlast))
(command "line" "_tan" p10 "_tan" p13 "")
(setq e11 (entlast))
(command "line" "_tan" p15 "_tan" p12 "")
(setq e12 (entlast))		;del.
(command "line" "_tan" p16 "_tan" p13 "")
(setq e13 (entlast))		;del.
(command "line" "_tan" p15 "_tan" p18 "")
(setq e14 (entlast))		;del.
;
(setq i1 (inters p8 p12 p10 p3 nil))
(command "line" "_int" i1 "_tan" p3 "")
(setq e15 (entlast))
(setq i2 (inters p12 p15 p10 p13 nil))
(command "line" "_int" i2 "_tan" p15 "")
(setq e16 (entlast))
(setq i3 (inters p15 p18 p16 p13 nil))
(command "line" "_int" i3 "_tan" p13 "")
(setq e17 (entlast))
(command "trim" e10 e11 "" "f" p9 p11 "" "")
(command "trim" e8 "" "f" p1 p21 "" "")
(command "trim" e8 "" "f" p5 p22 "" "")
;
(command "erase" e5 e6 e9 e12 e13 e14 "")
;
(command "array" e3 e4 e10 e11 "" "r" na "" pt)
(command "array" e16 e17 "" "r" (- na 1) "" pt)
;선경의center line
;(command "line" c1 c2 "")  (setq  (entlast))
;(command "line" c3 c4 "")  (setq  (entlast))
(command "line" p23 p24 "")
(setq e19 (entlast))		;center line
(command "chprop" e19 "" "la" "cen-m" "")
(command "mirror" e7 "" p7 p2 "n")
(setq e20 (entlast))
(command "mirror" e2 "" p7 p2 "n")
(setq e21 (entlast))
(command "mirror" e1 "" p7 p2 "n")
(setq e22 (entlast))
(command "mirror" e8 "" p7 p2 "n")
(setq e23 (entlast))
(command "mirror" e15 "" p7 p2 "n")
(setq e24 (entlast))
(command "mirror" e20 e21 e22 e23 e24 "" pk po "y")
(command "move" e20 e21 e22 e23 e24 "" p5 p19)
(setvar "osmode" osm)
)
);draw
;------------------
(textpage)
(princ
(strcat	"\n<입력>****************************************************************"
"\n                   재질= "
matl
" [인장강도(최소):"
(rtos tsl 2 2)
"(kg/mm2)]"
"\n              선경 (mm)= "
(rtos dw)
"\n            평균경 (mm)= "
(rtos d)
"\n          부하하중 (kg)= "
(rtos p 2 2)
"\n          유효권수 (>3)= "
(rtos na)
"\n                 총권수= "
(rtos nt)
"\n          자유높이 (mm)= "
(rtos hf)
"\n     양끝 연삭두께 (mm)= "
(rtos (- h (/ dw 2.0)) 2 2)
"\n<출력>****************************************************************"
"\n                휨 (mm)= "
(rtos de 2 2)
" (@"
(rtos p 2 2)
"kg)"
"\n    스프링상수 (kgf/mm)= "
(rtos k 2 3)
"\n          밀착높이 (mm)= "
(rtos hc 2 2)
"\n      부하시 총높이(mm)= "
(rtos hd 2 2)
" ("
(rtos hdr 2 2)
"%/@"
(rtos p 2 2)
"kg)"
"\n     피치 (mm):"
(rtos (* 0.5 d) 2 2)
"이하= "
(rtos pt 2 2)
"  "
txt
"\n   비틀림응력 (kgf/mm2)= "
(rtos so 2 2)
"\n수정비틀림응력(kgf/mm2)= "
(rtos s 2 2)
"\n          안전율 (>2.5)= "
(rtos ef 2 2)
" (인장강도/수정비틀림응력)  "
txt
"\n 스프링지수 (평균경/선경:4~22)= "
(rtos c 2 2)
"  "
txt
"\n종횡비 (자유높이/평균경=0.8~4)= "
(rtos jb 2 2)
"  "
txt
"\n           축적에너지 (kgf.mm)= "
(rtos u 2 2)
"\n          횡탄성계수 (kgf/mm2)= "
(rtos g)
"\n**********************************************************************"
"\n※Check Point: 피치,안전율,스프링지수,종횡비"
"\n※스프링재질: 스프링강(SPS3,SPS6,SPS7,SPS8,SPS9)/피아노선(SWP-A,SWP-B)"
"\n  경강선(SWB,SWC)/스테인레스선(STS304WPRA,SUS304WPBA)/인청동(C5191-WH)"
)
)
)
)					;압축스프링
;--------------------------------------------------------------------------
(if (= ans "3")			;인장스프링 
(progn
(princ
(strcat
"\n※CONDITION: 선경에 다른 인장강도는 평균및 최소기준"
"\n※  1항: 스프링강[SPS,SUP(JIS기호)]-판스프링및코일스프링용,열간성형,중대형"
"\n※2~5항: 냉간성형용"
"\n---------------------------------------------------------------------------"
"\n1.스프링강(SPS/SUP)          2.경강선(SWB,HSW)    3.피아노선(SWP-A,PW1)"
"\n4.스테인레스선(STS304WPRA)   5.인청동선(C5191-WH)"
"\n---------------------------------------------------------------------------")
)
(setq m (getint "\n재질/Select No. <3>: "))
(if (= m nil)
(setq m 3)
)
(menu-1);g,matl,dw
(menu-2);d평균경,지수c
(setq p (getreal "\n인장하중 (kg): "))
(setq hfo (+ (* do 2.0) (* dw 3.0)))
(princ (strcat "\n<<자유길이= 최소 "
     (rtos hfo)
     "이상/Hook to Hook/내경 선단>>"
)
)
(setq hf (getreal "\n자유 길이 (mm): "))
(princ "\n<<고정(셋팅)길이= 자유길이+휨길이>>")
(setq fl (getreal "\n고정(셋팅)길이 (mm): "))
(setq h1 (- hf (+ (* di 2.0) (* dw 2.0))))
(setq h (+ h1 dw))		;코일의 양끝 자유길이
(setq na (/ h dw))		;총권수
(setq na (+ na 0.5))
(setq na (rtos na 2 0))
(setq na (atoi na))
(if (< na 3)
(progn
(princ "\n<<유효권수가 적음! 3권이상)/Retry!>>")
(setq hf (getreal "\n자유 길이 (mm): "))
(princ "\n<<고정(셋팅)길이= 자유길이+휨길이>>")
(setq fl (getreal "\n고정(셋팅)길이 (mm): "))
(setq h1 (- hf (+ (* di 2.0) (* dw 2.0))))
(setq h (+ h1 dw))		;코일의 양끝 자유길이
(setq na (/ h dw))		;총권수
(setq na (+ na 0.5))
(setq na (rtos na 2 0))
(setq na (atoi na))
)
)
(setq hf1 (+ (* di 2.0) (+ (* na dw) (* dw 2.0)))) ;실 세팅자유길이
(setq h1 (- hf1 (+ (* di 2.0) (* dw 2.0))))
(setq h (+ h1 dw))		;코일의 양끝 자유길이
;
(setq de (- fl hf1))		;휨길이
(cond
((or (= m 2) (= m 3) (= m 4) (= m 5))
(setq ti (/ g (* 100 c)))
(setq pn (/ (* g (expt dw 4)) (* 255 (expt d 2))))
)				;pn=냉간스프링 초기장력
((= m 1) (setq pn 0))		;pn=열간스프링 초기장력
)
;ref-(setq na (/ (* g (expt dw 4) de) (* 8 (expt d 3) (- p pn)) ));총권수
(if (= m 1)
(progn
(setq k (/ (* g (expt dw 4)) (* 8 na (expt d 3)))) ;스프링상수(kg/mm)
(setq so (/ (* 8 d p) (* pi (expt dw 3))))         ;비틀림응력(kg/mm2)
)
(progn
(setq k (/ (- p pn) de))	;스프링상수(kg/mm)
(setq so (+ (/ (* 8 d p) (* pi (expt dw 3))) (/ g (* 100 c))));비틀림응력(kg/mm2)
)
)
(setq ts (+ (/ (- (* 4 c) 1) (- (* 4 c) 4)) (/ 0.615 c))) ;응력수정계수
(setq s (* ts so))		;수정비틀림응력(kg/mm2)
(setq u (/ (* (+ p pn) de) 2.0));축적에너지(kg.mm)
(setq pt (+ (/ de (- na 1)) dw));pitch(0.5d이하)
(setq ef (/ tsl s))		;안전율
(if (> ef 2.5)
(setq txt "OK!")
(setq txt "BAD!")
)
;DRAW-----------------------인장스프링/자유길이 
(setq an1 (strcase (getstring "\nDRAW ? <Y/N> <Y>: ")))
(if (= an1 "N")
(exit)
)
(if (or (= an1 "") (= an1 "Y"))
(progn
(graphscr)
(setq po (getpoint "\ninsertion point of bottom hook center "))
(setq	p1  (polar po (dtr 90.0) (/ di 2.0))
p2  (polar p1 (dtr 90.0) dw)
p3  (polar p2 (dtr 180.0) (/ d 2.0))
p4  (polar p3 (dtr 90.0) (/ dw 2.0))
p5  (polar p3 (dtr 270.0) (/ dw 2.0))
p6  (polar p2 (dtr 0.0) (/ d 2.0))
p7  (polar p6 (dtr 90.0) (/ dw 2.0))
p8  (polar p7 (dtr 90.0) (/ dw 2.0))
p9  (polar p8 (dtr 90.0) (/ dw 2.0))
p10 (polar po (dtr 150.0) (/ di 2.0))
p11 (polar po (dtr 150.0) (/ do 2.0))
p12 (polar po (dtr 270.0) (/ di 2.0))
p13 (polar p1 (dtr 89.0) 0.001)
p14 (polar p12 (dtr 90.0) (/ hf1 2.0))
p15 (polar p14 (dtr 180.0) 5.0)
p16 (polar p15 (dtr 0.0) 10.0)
p17 (polar p1 (dtr 90.0) (/ dw 2.0))
p18 (polar p17 (dtr 0.0) (/ dw 2.0))
p19 (polar p12 (dtr 270.0) (/ dw 2.0))
p20 (polar p19 (dtr 0.0) (/ dw 2.0))
p21 (polar p12 (dtr 90.0) hf1)
c1  (polar po (dtr 270.0) (+ (/ do 2.0) dw)) ;c1~c4 center line
c2  (polar po (dtr 0.0) (+ (/ do 2.0) dw))
c3  (polar po (dtr 180.0) (+ (/ do 2.0) dw))
c4  (polar p12 (dtr 90.0) (+ hf1 (* dw 2.0)))
)
;
(graphscr)
(setvar "osmode" 0)
(command "arc" "c" po p10 p1)
(setq e1 (entlast))
(command "arc" "c" po p11 p2)
(setq e2 (entlast))
(command "circle" p3 "d" dw)
(setq e3 (entlast))
(command "circle" p8 "d" dw)
(setq e4 (entlast))
(command "line" "_tan" p1 "_tan" p5 "")
(setq e5 (entlast))
(command "line" "_tan" p5 "_tan" p7 "")
(setq e6 (entlast))
(command "line" "_tan" p4 "_tan" p9 "")
(setq e7 (entlast))
(command "line" p10 p11 "")
(setq e10 (entlast))
;
(command "trim" e6 e7 "" "f" p3 p8 "" "")
(command "array" e3 e4 e7 "" "r" na "" dw)
(command "trim" e5 "" "f" po p13 "" "")
(command "pedit" e5 "y" "j" e1 e10 e2 "" "")
(setq e11 (entlast))
;
(command "line" c1 c4 "")
(setq e8 (entlast))
(command "line" c2 c3 "")
(setq e9 (entlast))
(command "circle" p17 "d" dw)
(setq e13 (entlast))
(command "circle" p19 "d" dw)
(setq e14 (entlast))
(command "line" p18 p20 "")
(setq e15 (entlast))
(command "mirror" e15 "" p1 p12 "n")
(setq e16 (entlast))
(command "chprop" e8 e9 e13 e14 e15 e16 "" "la" "cen-m" "")
;
(command "mirror" e11 "" p1 p12 "n")
(setq e12 (entlast))
(command "mirror" e12 "" p15 p16 "y")
(command "mirror" e9 "" p15 p16 "n")
;인장시 길이-------------------------
(setq	po1   (polar po (dtr 0.0) (+ do (/ do 2.0)))
p22   (polar p21 (dtr 0.0) (+ do (/ do 2.0)))
p23   (polar p22 (dtr 90.0) de)
p23-1 (polar p23 (dtr 270.0) (/ di 2.0))
p24   (polar po1 (dtr 90.0) (+ (/ di 2.0) dw))
p25   (polar p24 (dtr 180.0) (/ d 2.0))
p26   (polar p25 (dtr 90.0) (/ dw 2.0))
p27   (polar p25 (dtr 270.0) (/ dw 2.0))
p28   (polar p24 (dtr 0.0) (/ d 2.0))
p29   (polar p28 (dtr 90.0) dw)
p30   (polar p29 (dtr 270.0) (/ dw 2.0))
p31   (polar p29 (dtr 90.0) (/ dw 2.0))
p32   (polar p25 (dtr 90.0) pt)
p33   (polar p32 (dtr 90.0) (/ dw 2.0))
p34   (polar p32 (dtr 270.0) (/ dw 2.0))
p35   (polar p29 (dtr 90.0) pt)
p36   (polar p35 (dtr 270.0) (/ dw 2.0))
c5    (polar c1 (dtr 0.0) (+ do (/ do 2.0)))
c6    (polar p23 (dtr 90.0) (* dw 2.0))
)
;
(command "circle" p25 "d" dw)
(setq e18 (entlast))
(command "circle" p29 "d" dw)
(setq e19 (entlast))
(command "circle" p32 "d" dw)
(setq e20 (entlast))
(command "circle" p35 "d" dw)
(setq e21 (entlast))		;del.
(command "line" "_tan" p27 "_tan" p30 "")
(setq e22 (entlast))
(command "line" "_tan" p26 "_tan" p31 "")
(setq e23 (entlast))		;del.
(command "line" "_tan" p34 "_tan" p30 "")
(setq e24 (entlast))
(command "line" "_tan" p33 "_tan" p31 "")
(setq e25 (entlast))
(command "line" "_tan" p34 "_tan" p36 "")
(setq e26 (entlast))		;del.
;
(command "line" "_tan" p27 "_tan" p30 "")
(setq e27 (entlast))
(setq i1 (inters p26 p31 p34 p30 nil))
(command "line" "_int" i1 "_tan" p34 "")
(setq e28 (entlast))
(setq i2 (inters p34 p36 p33 p31 nil))
(command "line" "_int" i2 "_tan" p31 "")
(setq e29 (entlast))
;
(command "trim" e23 e22 "" "f" p25 p29 "" "")
(command "array" e18 e19 e22 e23 "" "r" na "" pt)
(command "array" e27 e29 e28 "" "r" (- na 1) "" pt)
(command "erase" e20 e21 e24 e25 e26 "")
;
(command "line" c5 c6 "")
(setq e30 (entlast))
(command "chprop" e30 "" "la" "cen-m" "")
(command "copy" e9 "" po p23-1)
(command "copy" e11 e13 e14 e15 e16 e9 "" po po1)
(command "copy" e12 "" p21 p23)
(setvar "osmode" osm)
)
)
;
(textpage)
(princ
(strcat
"\n<입력>*******************************************************************"
"\n                   재질= "
matl
" [인장강도(최소):"
(rtos tsl 2 2)
"(kg/mm2)]"
"\n              선경 (mm)= "
(rtos dw)
"\n            평균경 (mm)= "
(rtos d)
"\n          인장하중 (kg)= "
(rtos p 2 2)
"\n         고정 길이 (mm)= "
(rtos fl)
" (Hook to Hook:내경 상단)"
"\n   자유 길이(입력) (mm)= "
(rtos hf)
" (Hook to Hook:내경 상단)"
"\n<출력>*******************************************************************"
"\n   자유 길이(보정) (mm)= "
(rtos hf1)
" (Hook to Hook:내경 상단)"
"\n     자유길이(고리제외)= "
(rtos h)
"\n             총권수(>3)= "
(rtos na)
" (고리제외)"
"\n       휨(인장)길이(mm)= "
(rtos de 2 2)
"\n    스프링상수 (kgf/mm)= "
(rtos k 2 3)
"\n        인장시 피치(mm)= "
(rtos pt 2 2)
"\n             초장력(kg)= "
(rtos pn 2 2)
"\n   비틀림응력 (kgf/mm2)= "
(rtos so 2 2)
"\n수정비틀림응력(kgf/mm2)= "
(rtos s 2 2)
"\n          안전율 (>2.5)= "
(rtos ef 2 2)
" (인장강도/수정비틀림응력)"
"  "
txt
"\n 스프링지수 (평균경/선경:4~22)= "
(rtos c 2 2)
"\n           축적에너지 (kgf.mm)= "
(rtos u 2 2)
"\n          횡탄성계수 (kgf/mm2)= "
(rtos g)
"\n*************************************************************************"
"\n※ CONDITION: 선경에 따른 인장강도는 평균및 최소기준"
"\n※  인장하중: 초장력 포함"
"\n※Check Point: 안전율,스프링지수"
"\n※스프링재질: 스프링강(SPS3,SPS6,SPS7,SPS8,SPS9)/피아노선(SWP-A,SWP-B)"
"\n  경강선(SWB,SWC)/스테인레스선(STS304WPRA,SUS304WPBA)/인청동(C5191-WH)"
)
)
)
)					;if 인장스프링
;-------------------------------------------------------------------------------
(if (= ans "2")			;기존압축스프링
(progn
(princ
(strcat
"\n※Condition: 양끝연삭 압축스프링 / 선경에 다른 인장강도는 평균및 최소기준"
"\n※  1항: 스프링강[SPS,SUP(JIS기호)]-판스프링및코일스프링용,열간성형,중대형"
"\n※2~5항: 냉간성형용"
"\n----------------------------------------------------------------------------"
"\n1.스프링강(SPS/SUP)          2.경강선(SWB,HSW)    3.피아노선(SWP-A,PW1)"
"\n4.스테인레스선(STS304WPRA)   5.인청동선(C5191-WH)"
"\n----------------------------------------------------------------------------")
)
(setq m (getint "\n재질/Select No.: "))
(menu-1)				;선경dw/재질g
(setq an1 (strcase (getstring "\n<India./Outdia./Pcd> : ")))
(if	(= an1 "")
(exit)
)
(if	(= an1 "I")
(progn
(setq di (getreal "\nindia (mm): "))
(setq d (+ di dw))		;평균경
(setq do (+ di (* dw 2.0)))
)
)
(if	(= an1 "O")
(progn
(setq do (getreal "\noutdia (mm): "))
(setq d (- do dw))		;평균경
(setq di (- do (* dw 2.0)))
)
)
(if	(= an1 "P")
(progn
(setq dp (getreal "\npcd (mm): "))
(setq d dp)			;평균경
(setq di (- dp dw))
(setq do (+ dp dw))
)
)
(setq fl (getreal "\n자유길이 (mm): "))
(setq jb (/ fl d)) ;종횡비
(setq na (getreal "\n유효권수: "))
;(setq ef1 (getreal "\n목표 안전율 <1>: "))
; (if (= ef1 nil) (setq ef1 1.0))          
(setq nt (+ na 1.5))	;총권수
(setq hc (+ (* (- nt 1.0) dw) (/ dw 3.0))) ;밀착높이(mm)
;(setq de (/ (* 8.0 na (expt d 3.0) p) (* g (expt dw 4.0)))) 
(setq c (/ d dw))		           ;스프링지수(4~22) 
(setq ts (+ (/ (- (* 4 c) 1) (- (* 4 c) 4)) (/ 0.615 c))) ;응력수정계수     
(setq k (/ (* g (expt dw 4.0)) (* 8.0 na (expt d 3.0))))  ;스프링상수(kg/mm)
 (cond
  ((= an1 "I") (setq sd di) (setq st "내경"))
  ((= an1 "O") (setq sd do) (setq st "외경"))
  ((= an1 "P") (setq sd dp) (setq st "평균경"))
 )
(setq fd (* fl 0.8));80%높이
(setq pk (* fd k))  ;80%하중
;(setq so (/ (* 8.0 d p) (* pi (expt dw 3.0)))) ;비틀림응력(kg/mm2)
;(setq s (* ts so))		;수정비틀림응력(kg/mm2)            
;(setq u (/ (* p de) 2.0))	;축적에너지(kg.mm)                 
;(setq ef (/ tsl s))		;안전율/tsl:인장강도               
(textpage)
(princ
(strcat	"\n<입력>****************************************************************"
"\n                   재질= "
matl
" [인장강도(최소):"
(rtos tsl 2 2)
"(kg/mm2)]"
"\n              선경 (mm)= "
(rtos dw)
"\n              " st " (mm)= "
(rtos sd)
"\n          자유길이 (mm)= "	
(rtos fl)
"\n               유효권수= "
(rtos na)
;"\n                안전율 = "
;(rtos ef1 2 2)
;" (인장강도/수정비틀림응력)"
"\n<출력>****************************************************************"
"\n                 밀착높이 (mm)= "
(rtos hc 2 2)	
"\n           스프링상수 (kgf/mm)= "
(rtos k 2 3)

"\n                    하중 (kgf)= "
(rtos pk 2 3) " (@ 80%)"

"\n               하중시 높이 mm)= "
(rtos fd 2 3) " [@ 80% / " (rtos pk) "(kgf)]"	

	
"\n종횡비 (자유높이/평균경=0.8~4)= "
(rtos jb 2 3)
;;;;"\n          비틀림응력 (kgf/mm2)= "
;;;(rtos so 2 2)
;;;"\n      수정 비틀림응력(kgf/mm2)= "
;;;(rtos s 2 2)
;;;"\n 스프링지수 (평균경/선경:4~22)= "
;;;(rtos c 2 2)
;;;"\n           축적에너지 (kgf.mm)= "
;;;(rtos u 2 2)
"\n           횡탄성계수(kgf/mm2)= "
(rtos g)
"\n**********************************************************************"
"\n※스프링재질: 스프링강(SPS3,SPS6,SPS7,SPS8,SPS9)/피아노선(SWP-A,SWP-B)"
"\n경강선(SWB,SWC)/스테인레스선(STS304WPRA,SUS304WPBA)/인청동(C5191-WH)"
)
)
)
)					;현품압축스프링
;-------------------------------------------------------------------------
(if (= ans "4")
(progn
(princ "\n-CORE SPRNG(1)-")
(setq an (getstring
 "\nSelect No.<1.LIGHT  2.MEDIUM  3.HEAVY  4.EXTRA HEAVY>: "
)
)
(cond
((= an "1") (DIESPRING-LIGHT))
((= an "2") (DIESPRING-MEDIUM))
((= an "3") (DIESPRING-HEAVY))
((= an "4") (DIESPRING-EXTRA))
((= an "") (exit))
)
(if (= an1 nil)
(exit)
)
(setq od (nth 0 size)	;o.d
id (nth 1 size)		;i.d
h  (nth 2 size)		;height
r  (nth 3 size)		;rate
l  (nth 4 size)		;load
d  (nth 5 size)		;deflection
)
(setq r (* r 0.102))
(setq l (* l 0.102))
(princ
(strcat
"\n------------------------------------------------------------------------"
"\nSelected: O.D(mm)="
(rtos od 2 1)
"             I.D(mm)="
(rtos id 2 1)
"           Height(mm)="
(rtos h 2 1)
"\n          Rate(kgf/mm)="
(rtos r 2 2)
"     Load(kgf)="
(rtos l 2 2)
"    Deflection(mm)="
(rtos d 2 1)
"\n-----------------The Load & Deflection is Maximum Data------------------"
)
)
)
)					  ;die spring(1)
;-------------------------------------------------------
(if (= ans "5")
(progn
(princ (strcat "\n------------CORE SPRNG (2)-----------"
     "\n1.LIGHTEST    2.LIGHT     3.MEDIUM"
     "\n4.HEAVY       5.EXTRA HEAVY"
     "\n-------------------------------------"
)
)
(setq an (getstring "\nSelect No.: "))
(cond
((= an "1") (DIESPRING1-LIGHTEST))
((= an "2") (DIESPRING2-LIGHT))
((= an "3") (DIESPRING3-MEDIUM))
((= an "4") (DIESPRING4-HEAVY))
((= an "5") (DIESPRING5-EXTRAHEAVY))
((= an "") (exit))
)
)
);die spring(2)
;---------------------------------------------------------
(if (= ans "6")
(progn
 (setq od (getreal "\nOut DIA.(mm) <25>: "))
  (if (= od nil) (setq od 25.0))
 (setq id (getreal "\nIn DIA.(mm) <12.5>: "))
  (if (= id nil) (setq id 12.5))
 (setq h  (getreal "\nFree Height(mm) <25>: "))
  (if (= h nil) (setq h 25.0)) 
 (setq tn (getint "\nTotal Number Of Coils [정수/양끝 연식부 제외] (mm) <5>: "))
  (if (= tn nil) (setq tn 5))
 (setq ct (getreal "\nSQ.Coil Thickness (Height) (mm) <2.5>: "))
  (if (= ct nil) (setq ct 2.5))
 (graphscr)
 (setq po (getpoint "\ninsertion point of bottom center ")) 
 (setq gak (dtr 4.0));coil degree
  (if (< od 15) (setq th 0.2)) ;bottm center coil thickness
  (if (> od 15) (setq th 0.5)) 
 (setq vt (/ ct (cos gak)));coil vertical height
 (setq ht (* (tan gak) od));right bottom coil total height
 (setq et (+ (* (tan gak) (/ od 2.0)) th));right bottom coil thickness
 (setq sp1 (- h (+ (* tn vt) ht)))        ;space between coil
 (setq sp (/ sp1 (- tn 1)))
 (setq ar (+ sp vt)) ;array space
 (setvar "osmode" 0)
 (setq p1 (polar po (dtr 0.0) (/ od 2.0)))
 (setq p2 (polar p1 (dtr 90.0) et))
 (setq p3 (polar p1 (dtr 90.0) ht))
 (setq p4 (polar po (dtr 90.0) th))
 (setq p5 (polar po (dtr 180.0) (/ od 2.0)))
 (setq p6 (polar p5 (dtr 90.0) vt))
 (setq p7 (polar p3 (dtr 90.0) vt))
 (setq p8 (polar po (dtr 180.0)(/ id 2.0)))
 (setq p9 (polar p8 (dtr 0.0) id))
 (setq p10 (polar p8  (dtr 90.0) (* (tan gak) (/ (- od id) 2.0))))
 (setq p11 (polar p10 (dtr 90.0) vt))
 (setq p13 (polar p9  (dtr 90.0) (* (tan gak) (+ id (/ (- od id) 2.0)))))
 (setq p12 (polar p13 (dtr 90.0) vt))
 (setq p14 (polar p9  (dtr 90.0) (+ th (* (tan gak) (/ id 2.0)))))
 (setq p15 (polar po  (dtr 90.0) h)) ;top center
 (setq p16 (polar p15 (dtr 0.0) (/ od 2.0)))  ;top right od
 (setq p17 (polar p15 (dtr 180.0) (/ od 2.0)));top left od 
 ;right bottom 연삭 coil thickness
 (command "line" p5 p1 "") (setq e1 (entlast))
 (command "line" p1 p2 "") (setq e2 (entlast))
 (command "line" p2 p4 "") (setq e3 (entlast))
 (command "line" p4 po "") (setq e4 (entlast))
 (command "pedit" e1 "y" "j" e2 e3 e4 "" "") (setq e5 (entlast))
 ;bottom 1st coil
 (command "line" p5 p3 "") (setq e6 (entlast))
 (command "line" p5 p6 "") (setq e7 (entlast))
 (command "line" p6 p7 "") (setq e8 (entlast))
 (command "line" p3 p7 "") (setq e9 (entlast))
 (command "pedit" e6 "y" "j" e7 e8 e9 "" "") (setq e10 (entlast))
 ;
 (command "line" p10 p11 "") (setq e11 (entlast)) ;inside hidden line
 (command "line" p13 p12 "") (setq e12 (entlast))
 (command "line" p9 p14 "")  (setq e13 (entlast))
 (command "chprop" e11 e12 e13 "" "la" "hid-r" "")
 (command "array" e10 e11 e12 "" "r" tn "" ar)
 ;
 (setq p18 (polar p17 (dtr 270.0) et))
 (setq p19 (polar p15 (dtr 270.0) th))
 (setq p20 (polar p15 (dtr 180.0) (/ id 2.0))) 
 (setq p21 (polar p20 (dtr 270.0) (+ th (* (tan gak) (/ id 2.0)))))
 (command "pline" p16 p17 p18 p19 p15 "")
 ;
 (command "line" p20 p21 "")
 (command "chprop" (entlast) "" "la" "hid-r" "")
 ;
 (setq p22 (polar p15 (dtr 90.0) 2.0)) ;center line
 (setq p23 (polar po  (dtr 270.0) 2.0))
 (command "line" p22 p23 "")
 (command "chprop" (entlast) "" "la" "cen-m" "")
 ;
 (setq p24 (polar p5 (dtr 90.0) (+ vt sp)))
 (command "line" p3 p24 "") (setq e14 (entlast)) 
 (setq ent (entget e14))      
 (setq l1 (cdr (assoc 10 ent)))
 (setq l2 (cdr (assoc 11 ent)))   
 (setq ang1 (angle l1 l2))
 (setq ang (- (dtr 180.0) ang1)) 
 (setq p25 (polar p3 (dtr 180.0) (+ id (/ (- od id) 2.0))))
 (setq p26 (polar p25 (dtr 90.0) (* (tan ang) (+ id (/ (- od id) 2.0)))))
 (command "erase" e14 "")
 (command "line" p26 p24 "") (setq e15 (entlast)) 
 (setq ent1 (entget e15))      
 (setq lp (cdr (assoc 10 ent1)))
 (command "copy" e15 "" lp p7)  (setq e16 (entlast))
 (command "array" e15 e16 "" "r" (- tn 1) "" ar)
 (princ "\n--연삭부 두께 및 코일 경사도는 실제와 다름--")
)
)
;-----------------------------------
(princ "\n -Press anykey for Exit-")
(grread)
(graphscr)
;-----------------------------------
(command "undo" "e")
(setvar "cmdecho" ocmde)
(setvar "osmode" osm)
(setq *error* olderr)
(princ)
)
;----------------------------------------------------------
(princ "\n\tSPRING [typing SPRING]: 2011.10 / by K.W.PARK")
(princ)
