(defun dtr (a)(* pi (/ a 180.0)))
(defun rtd (a)(/ (* a 180.0) pi))
(grapHscr)
(defun c:qs()  (command "qsave")(princ))
(defun c:oo()  (command "open")(princ))
(defun c:qq()  (command "quit" "y")(princ))
(defun c:di()  (command "dist")(princ))
(defun c:pg()  (command "purge" "a")(princ))
(defun c:sc()  (command "scale")(princ))
(defun c:e()   (command "erase")(princ))
(defun c:m()   (command "move")(princ))
(defun c:cc()  (command "copy")(princ))
(defun c:so()  (command "solid")(princ))
(defun c:ls()  (command "ltscale")(princ))
(defun c:ar()  (command "array")(princ))
(defun C:l()   (command "line")(princ))
(defun c:st()  (command "stretch" "c")(princ))
(defun c:ci()  (command "circle")(princ))
(defun c:li()  (command "list")(princ))
(defun c:a()   (command "arc")(princ))
(defun c:de()  (command "ddedIt")(princ))
(defun c:pl()  (command "pline")(princ))
(defun c:py()  (command "polygon")(princ))
(defun c:do()  (command "donut")(princ))
(defun c:el()  (command "ellipse")(princ))
(defun c:dt()  (command "dtext") (princ))
(defun c:ch()  (command "change")(PRINC))
(defun c:ro()  (command "rotate")(princ))
(defun c:mi()  (command "mirror")(princ))
(defun c:et()  (command "extend")(princ))
(defun c:dm()  (command "ddmodify")(princ))
(defun c:ii()  (command "ddinsert")(princ))
(defun c:b()   (command "break")(princ))
(defun c:tr()  (command "trim")(princ))
(defun c:fl()  (command "fillet")(princ))
(defun c:fr()  (command "fillet" "r")(princ))
(defun c:ff()  (command "fillet" "r" "0" "fillet" "t" "t" "fillet")(princ))
(defun c:cf()  (command "chamfer")(princ))
(defun c:o()   (command "offset")(princ))
(defun c:r()   (command "redraw")(princ))
(defun c:ep()  (command "explode")(princ))
(defun c:pe()  (command "pedit")(princ))
(defun c:sp()  (command "spline")(princ))
(defun c:za()  (command "'zoom" "a")(princ))
(defun c:zp()  (command "'zoom" "p")(princ))
(defun c:z1()  (command "'zoom" "0.5x")(princ))
(defun c:z2()  (command "'zoom" "2x")(princ))
(defun c:da()  (command "dim" "ali")(princ))
(defun c:dh()  (command "dim" "hor")(princ))
(defun c:dv()  (command "dim" "ver")(princ))
(defun c:dr()  (command "dim" "rad")(princ))
(defun c:dd()  (command "dim" "dia")(princ))
(defun c:dl()  (command "dim" "leader")(princ))
(defun c:dLI() (command "dim" "linear")(princ))
(defun c:dg()  (command "dim" "angular")(princ))
(defun c:db()  (command "dim" "baseline")(princ))
(defun c:dc()  (command "dim" "cont")(princ))
(defun c:dor()  (command "dim" "ordinate")(princ))
(defun c:ds()  (command "dimscale")(princ))
(defun c:bm()  (command "blipmode")(princ))
(defun c:t()   (command "extend")(princ))

;|
(defun f:makeLtype (uLtype)
    (if (not (tblsearch "ltype" uLtype))
        (command "LINETYPE" "L" uLtype "zwcad" "")
        (princ "\n로드됨")
    )
)
|;

;단축키 1 : 중심선 / 빨강 / 0.18mm
(defun c:1()  (setq a (ssget)) (command "change" a "" "p" "lt" "center" "c" "1" "lw" "0.18" ""))(princ)
;단축키 2 : 은선 / 노랑 / 0.15mm
(defun c:2()  (setq a (ssget)) (command "change" a "" "p" "lt" "hidden" "c" "2" "lw" "0.15" ""))(princ)
;단축키 3 : 외형선 / 녹색 / 0.3mm
(defun c:3()  (setq a (ssget)) (command "change" a "" "p" "lt" "CONTINUOUS" "c" "3" "lw" "0.3" ""))(princ)
;단축키 4 : 실선 / 하늘색 / 0.15mm
(defun c:4()  (setq a (ssget)) (command "change" a "" "p" "lt" "CONTINUOUS" "c" "4" "lw" "0.15" ""))(princ)
;단축키 5 : 가상선 / 파랑색 / 0.15mm
(defun c:5()  (setq a (ssget)) (command "change" a "" "p" "lt" "PHANTOM2" "c" "5" "lw" "0.15" ""))(princ)
(defun c:6()  (setq a (ssget)) (command "change" a "" "p" "la" "6" "lt" "bylayer" "c" "byl" ""))(princ)
(defun c:7()  (setq a (ssget)) (command "change" a "" "p" "la" "7" "lt" "bylayer" "c" "byl" ""))(princ)
(defun c:8()  (setq a (ssget)) (command "change" a "" "p" "la" "8" "lt" "bylayer" "c" "byl" ""))(princ)
(defun c:9()  (setq a (ssget)) (command "change" a "" "p" "la" "9" "lt" "bylayer" "c" "byl" ""))(princ)
(defun c:10()  (setq a (ssget)) (command "change" a "" "p" "la" "10" "lt" "bylayer" "c" "byl" ""))(princ)
; CHGTEXT.LSP: CHANGE TEXT PROGRAM
(defun c:ct (/ p l n e as os ns st s osl nsl sl si chi chf chm)
  (setq p (ssget))
  (if p
  (progn (setq osl (strlen (setq os (getstring "\nOld string: " t))))
	 (setq nsl (strlen (setq ns (getstring "\nNew string: " t))))
	 (setq l 0 chi 0 chm 0 n (sslength p))
	(if (/= os "")
	(progn
	  (while (< l n)
	(if (= "TEXT" (cdr (assoc 0 (setq e (entget (ssname p l))))))
	(progn
	  (setq chf nil si 1)
	  (setq s (cdr (setq as (assoc 1 e))))
	  (while (= osl
		 (setq sl (strlen (setq st (substr s si osl)))))
		(if (= st os)
		(progn
		  (setq s (strcat (substr s 1 (1- si))
			ns (substr s (+ si osl))))
		  (setq si (+ si (- nsl 1)))
		  (setq chf T)
		  (setq chi (1+ chi))
		)
		)
		(setq si (1+ si))
	  )
	  (if chf
	  (progn
		(setq e (subst (cons 1 s) as e))
		(entmod e)
		(setq chm (1+ chm))
	  )
	  )
	)
	)
	(setq l (1+ l))
	  )
	)
	)
  )
  )
  (terpri)
  (princ "Chnaged ")(princ chi)
  (princ " place(s) on ") (princ chm)
  (princ " text line.")
  (princ)
)

(vmon)
;--------------- Extention a line ----------------------------
(defun C:TT ()
	(while (null (setq e (entsel "\nPick a line to extent:")) ))
	(setq en (car e) sp (cadr e))
	(setq e (entget en))
	(setq pt1 (cdr (assoc 10 e)));get one point
	(setq pt2 (cdr (assoc 11 e)));get other point
	(setq l_half (/ (distance pt1 pt2) 2))
	(setq l_pt1 (distance pt1 sp ))
	(setq p10 10 p11 11)
	(if (< l_pt1 l_half) (progn
		(setq temp pt1 pt1 pt2 pt2 temp)
		(setq temp p10 p10 p11 p11 temp) )
	)
	(setq ang (angle pt1 pt2))
	(setq l_ext (getdist pt2 "\nLenth ?"))
	(setq pt_ext (polar pt2 ang l_ext))
	(setq e
		(subst (cons p11 pt_ext)
			   (assoc p11 e)
			e
		)
	)
	(entmod e)
	(terpri)
)
;------------------- Layer change program ----------------------
(defun C:SD ( / ss e n)
  (princ "Select objects to be changed .. \n")
  (setq ss (ssget))                     ;general selection set
  (if ss (progn                         ;if any objects selected
	 (setq e (car (entsel "Pick an object on desired layer : ")))
	 (if e (progn
		(setq e (entget e)) ;get its data groups
		(setq n (cdr (assoc 8 e))) ;group 8 means layer
		(command "CHANGE" ss "" "PROP" "LAYER" N "")
	 ))
))
)
;---------- Set current layer to that of an given object ---------
(defun C:SLY (/ e n)
  (setq e (car (entsel "Pick an object on the desired layer : ")))
  (if e (progn
	(setq e (entget e))             ;get entity data groups
	(setq n (cdr (assoc 8 e)))      ;group 8 is layer name
	(command "LAYER" "SET" n "")    ;issue "layer set" cmnd
))
)
;;;;;;CHANGE TEXT;;;
(defun chng ()
	 (if (/= an1 "")
	 (progn (setq ts vs)
		(setq n 7)
		(tgi)
	 )
	 )
	(if (/= an2 "")
	 (progn (setq ts (atof an2))
		(setq n 40)
		(tgi)
	 )
	 )
	 (if (/= an3 "")
	 (progn (setq f1 (assoc 72 b1))
		(setq f (cdr f1))
		(if (= f 5)
			(progn (setq f2 (cons 72 0))
			   (setq b1 (subst f2 f1 b1))
			   (entmod b1)
			   (setq c1 (assoc 11 b1))
			   (setq c2 '(11 0.0 0.0 0.0))
			   (setq b1 (subst c2 c1 b1))
			   (entmod b1)
			)
		)
		(setq ts (atof an3))
		(setq n 41)
		(tgi)
	 )
	 )
)
;
(defun tgi ()
	 (setq r1 (assoc n b1))
	 (setq r2 (cons n ts))
	 (setq b1 (subst r2 r1 b1))
	 (entmod b1)
)
(defun sel ()
	 (princ "\nDo you want the change English TEXT (Y/N) :")
	 (setq ss (getstring))
	 (setq ss (strcase ss))
	 (if (or (= ss "") (= ss "Y"))
	 (tex)
	 (babo)
	 )
)
(defun babo ()
	 (setq a (ssget))
	 (setq n (sslength a))
	 (setq index 0)
	 (princ "\nYou don't want to change Font style, then press RETURN key!")
	 (princ "\nInput Font style No <1;hsg 2;hng 3;hcm 4;hdm>: ")
	 (setq an1 (getstring))
	 (if (/= an1 "")
	 (if (= an1 "1")
		 (setq vs "HSG")
		 (if (= an1 "2")
		 (setq vs "HNG")
		 (if (= an1 "3")
			 (setq vs "HCM")
			 (if (= an1 "4")
			 (setq vs "HDM")
			 )
		 )
		 )
	 )
	 )
	 (princ "\nYou don't want to change Text height, then press RETURN key!")
	 (setq an2 (getstring "\nInput Text height: "))
	 (princ "\nYou don't want to change Width factor, then press RETURN key!")
	 (setq an3 (getstring "\nInput Width factor: "))
	 (rpn)
)
;
(defun tex ()
	 (setq a (ssget))
	 (setq n (sslength a))
	 (setq index 0)
	 (princ "\nYou don't want to change Font style, then press RETURN key!")
	 (princ "\nInput Font style No <1;romans 2;romand 3;romanc 4;romant 5;scripts>: ")
	 (setq an1 (getstring))
	 (if (/= an1 "")
	 (if (= an1 "1")
		 (setq vs "ROMANS")
		 (if (= an1 "2")
		 (setq vs "ROMAND")
		 (if (= an1 "3")
			 (setq vs "ROMANC")
			 (if (= an1 "4")
			 (setq vs "ROMANT")
			 (if (= an1 "5")
				 (setq vs "SCRIPTS")
			 )
			 )
		 )
		 )
	 )
	 )
	 (princ "\nYou don't want to change Text height, then press RETURN key!")
	 (setq an2 (getstring "\nInput Text height: "))
	 (princ "\nYou don't want to change Width factor, then press RETURN key!")
	 (setq an3 (getstring "\nInput Width factor: "))
	 (rpn)
)
;
(defun rpn ()
	 (repeat n
	  (setq b1 (entget (ssname a index)))
	  (setq index (+ 1 index))
	  (setq b (assoc 0 b1)
		bn (cdr b)
	  )
	  (if (= bn "TEXT")
		  (chng)
	  )
	 )
)
;
(defun c:tchg ()
	 (sel)
	 (princ "\n    The process of program is quited.")
	 (princ)
)

(DEFUN C:CUT()
   (SETQ PT(entsel "\nSelect object :"))
   (setq pt1(getpoint "\nCutting point :"))
   (COMMAND "BREAK" PT "f" PT1 PT1 ))

(DEFUN C:zx( / KAR1 KAR2 KAR3 KAR4 KAR5)
   (GRAPHSCR)
   (SETQ KAR1(SSGET))  f
   (SETQ KAR2(SSNAME KAR1 0))
   (SETQ KAR3(ENTGET KAR2))
   (SETQ KAR4(ASSOC 12 KAR3))
   (SETQ KAR5(CDR KAR4))
   (COMMAND "ROTATE" KAR2 "" KAR5 "180" ))
;
(DEFUN C:zz( / KAR1 KAR2 KAR3 KAR4 KAR5)
   (GRAPHSCR)
   (SETQ KAR1(SSGET))  f
   (SETQ KAR2(SSNAME KAR1 0))
   (SETQ KAR3(ENTGET KAR2))
   (SETQ KAR4(ASSOC 10 KAR3))
   (SETQ KAR5(CDR KAR4))
   (COMMAND "ROTATE" KAR2 "" KAR5 "180" ))
;

  (defun C:MTR ()
	(setvar "cmdecho" 0)
	(prompt "select cutting edge") (terpri)
	(setq ce (ssget)) (terpri)
	(prompt "select objects to trim:") (terpri)
	(setq pnt1 (getpoint "first point")) (terpri)
	(setq pnt2 (getcorner pnt1 "2nd pnt")) (terpri)
	(setq ss (ssget "c" pnt1 pnt2)
	  ls (sslength ss)
	  no -1
	)
	(command "trim" ce "")
	(repeat ls
	(setq no (1+ no))
	(command (list (ssname ss no) pnt2))
	)
	(command "")
	(setvar "cmdecho" 1)
	(prin1)
  )
(defun C:Met ()
	(setvar "cmdecho" 0)
	(prompt "select extend edge") (terpri)
	(setq ce (ssget)) (terpri)
	(prompt "select objects to extend:") (terpri)
	(setq pnt1 (getpoint "first point")) (terpri)
	(setq pnt2 (getcorner pnt1 "2nd pnt")) (terpri)
	(setq ss (ssget "c" pnt1 pnt2)
	  ls (sslength ss)
	  no -1
	)
	(command "extend" ce "")
	(repeat ls
	(setq no (1+ no))
	(command (list (ssname ss no) pnt2))
	)
	(command "")
	(setvar "cmdecho" 1)
	(prin1)
  )

(defun c:wt(/ ktms kl ksl kaddn kaddn1 ktol  )
  (setq ktms (ssget))
  (if ktms
	 (progn
	(setq ksl(sslength ktms) kl 0 kaddn 0)
	(while (< kl ksl)
	   (setq ktol (entget (ssname ktms kl)))
	   (setq kaddn1(cdr(assoc 1 ktol)))
	   (if (and(= (cdr(assoc 0 ktol)) "TEXT")(or(> (ascii kaddn1) 46)(< (ascii kaddn1) 58)))
		   (progn
		(setq kaddn(+ kaddn (atof kaddn1)))
	   )   )
	   (setq kl(+ kl 1))
  )  )  )
  (terpri)
  (princ kaddn)
  (princ)
)


(VMON)
(DEFUN C:FD()
   (SETQ CHTS(SSGET))
   (SETQ CHTL(SSLENGTH CHTS))
   (SETQ CHTI 0)
   (REPEAT CHTL
	  (setvar "highlight" 1)
	  (SETQ CHTE_N(SSNAME CHTS CHTI))
	  (SETQ CHTE_L(ENTGET CHTE_N))
	  (SETQ CHTE_P(cdr(ASSOC 0 CHTE_L)))
	  (SETQ CHTE100(GETSTRING "Enter the text to change :"))(terpri)
	  (IF (= CHTE_P "TEXT")
	  (PROGN
		 (SETQ CHTE_ln(SUBST (cons 1 chte100) (ASSOC 1 CHTE_L) chte_l))
		 (ENTMOD CHTE_ln)
	  )  )
	  (SETQ CHTI(+ CHTI 1))
   )
)

; dimension line modify
(defun C:LL ()
   (setq olderr  *error*  *error* newerr)
	(print " select 2 line to make one ") (setq w1 (ssget))
	(setq ll1 (ssname w1 0)) (setq ll2 (ssname w1 1)) (setq l1 (entget (ssname w1 0))) (setq l2 (entget (ssname w1 1)))
	(setq x1 (car (setq v1 (cdr (setq k1(assoc 10 l1)))))) (setq y1 (car (cdr v1)))
	(setq x2 (car (setq v2 (cdr (setq k2(assoc 11 l1)))))) (setq y2 (car (cdr v2)))
	(setq x3 (car (setq v3 (cdr (assoc 10 l2))))) (setq y3 (car (cdr v3)))
	(setq x4 (car (setq v4 (cdr (assoc 11 l2))))) (setq y4 (car (cdr v4)))
	(setq d1 (+ (abs (- x1 x3)) (abs (- y1 y3)))) (setq d2 (+ (abs (- x1 x4)) (abs (- y1 y4))))
	(if (> d1 d2) (progn (setq d3 (+ (abs (- x2 x3)) (abs (- y2 y3))))
	(if (> d1 d3) (setq xh1 x1 yh1 y1 xl1 x3 yl1 y3))  (if (< d1 d3) (setq xh1 x2 yh1 y2 xl1 x3 yl1 y3))  ))
	(if (< d1 d2) (progn (setq d3 (+ (abs (- x2 x4)) (abs (- y2 y4))))
	(if (> d2 d3) (setq xh1 x1 yh1 y1 xl1 x4 yl1 y4))  (if (< d2 d3) (setq xh1 x2 yh1 y2 xl1 x4 yl1 y4))  ))
	(entdel ll2) (setq l1 (subst (cons 10 (list xh1 yh1)) k1 l1)) (setq l1 (subst (cons 11 (list xl1 yl1)) k2 l1)) (entmod l1)
   (setq *error* olderr)              ; Restore old *error* handler
	(prin1)
)

(VMON)
(defun c:sca()
	  (graphscr)
	  (NEXT)
	  (setvar "blipmode" 1)
	  (setvar "cmdecho" 1)
	  (princ)
)

(defun NEXT()
	  (SETQ sela(SSGET))
	  (SETQ NO(SSLENGTH sela))
	  (setq INDEX 0)
	  (SETQ TEXT1(GETREAL "Enter the Scale Factor to First:"))(terpri)
	  (SETQ TEXT2(GETREAL "Enter the Scale Factor to Last:"))(terpri)
	  (setq ref (/ text2 text1))
	  (REPEAT NO
	  (SETQ C(SSNAME sela INDEX))
	  (SETQ D(ENTGET C))
	  (SETQ enti (cdr (ASSOC 0 D)))
	(setq index (+ 1 index))
	 (if (= "TEXT" enti)
	 (TEXTA))
	 (if (= "SOLID" enti)
	 (arrow))
	 (if (= "line" enti)
	  (lline))
 ))

(DEFUN TEXTA()
	  (SETQ T_START (ASSOC 11 (CDR D)))
	  (SETQ T_STarT1 (CADR T_START))
	  (SETQ T_STAR (CDR T_START))
	  (SETQ ID1Y (CADDR T_START))
	  (SETQ DIS1 (CDR (ASSOC 40 (CDR D))))
	  (SETQ ANG1 (CDR (ASSOC 50 (CDR D))))
	  (SETQ ANG2 (RTD ANG1))
	  (IF (= ANG2 0)
	  (TEXT0))
	  (IF (= ANG2 90)
	  (TEXT90))
	  (IF (and (> ANG2 0) (< ANG2 90))
	  (TEXT45))
	  (IF (> ANG2 90)
	  (TEXT315))
   )

(DEFUN TEXT0 ()
	  (SETQ ID1XY (POLAR T_STAR (DTR 270) DIS1))
	  (command  "scale" c "" ID1XY ref "")
   )

(DEFUN TEXT90 ()
	  (SETQ ID2XY (POLAR T_STAR (DTR 0) DIS1))
	  (command  "scale" C "" ID2XY ref "")
  )

(DEFUN TEXT45 ()
	  (SETQ ANG3 (+ 270 ANG2))
	  (SETQ ID3XY (POLAR T_STAR (dtr ANG3) DIS1))
	  (command  "scale" C "" ID3XY ref "")
 )

(DEFUN text315 ()
	   (SETQ ANG4 (- ANG2 90))
	   (SETQ ID4XY (POLAR T_STAR (dtr ANG4) DIS1))
	   (COMMAND "SCALE" C "" ID4XY REF "")
  )


(DEFUN ARROW()
	  (SETQ A_START (CDR (ASSOC 12 D)))
	  (command  "scale" C "" A_start ref "")
	)
(defun lline ()
	   (SETQ lp1 (cdr (ASSOC 11 (CDR D))))
	   (setq lp2 (polar lp1 (dtr 135) 0.001))
	   (setq lp3 (polar lp1 (dtr 315) 0.001))
	   (setq refa (abs ref))
	   (command "scale" c "" lp1 refa "")
)
(DEFUN C:TE (/ SE1 NO1 INDEX IN1 IN2 IN3 IN4 FINAL)
	(SETQ SE1 (SSGET))
	(SETQ NO1 (SSLENGTH SE1))
	(SETQ INDEX 0)
	(REPEAT NO1
	   (SETQ IN1 (SSNAME SE1 INDEX))
	   (SETQ IN2 (ENTGET IN1))
	   (SETQ IN3 (CDR (ASSOC 0 (CDR IN2))))
	   (SETQ IN4 (ASSOC 8 (CDR IN2)))
	 (IF (= "TEXT" IN3)
	   (PROGN
		 (SETQ FINAL (SUBST  (CONS 8 "2") IN4 IN2))
		 (ENTMOD FINAL)
	   )
	 )
   (SETQ INDEX (+ 1 INDEX))
  )
)

(DEFUN C:CAP (/ SE1 NO1 INDEX IN1 IN2 IN3 C1 C2 C3)
	(SETQ SE1 (SSGET))
	(SETQ NO1 (SSLENGTH SE1))
	(SETQ INDEX 0)
	(REPEAT NO1
	   (SETQ IN1 (SSNAME SE1 INDEX))
	   (SETQ IN2 (ENTGET IN1))
	   (SETQ IN3 (CDR (ASSOC 0 (CDR IN2))))
	 (IF (= "TEXT" IN3)
	   (PROGN
		 (SETQ C1 (CDR (ASSOC 1 (CDR IN2))))
		 (SETQ C2 (STRCASE C1))
		 (SETQ C3 (SUBST (cons 1 C2) (cons 1 C1) IN2))
		 (ENTMOD C3)
	   )
	 )
   (SETQ INDEX (+ 1 INDEX))
  )
)
(DEFUN C:WTT ()
	(SETQ SE_1 (SSGET))
	(SETQ NO_1 (SSLENGTH SE_1))
	(SETQ INDEX 0)
	(SETQ USER1 (GETreal "\nENTER NO.:"))
	(REPEAT NO_1
	   (SETQ IN_1 (SSNAME SE_1 INDEX))
	   (SETQ IN_2 (ENTGET IN_1))
	   (SETQ IN_3 (CDR (ASSOC 0 (CDR IN_2))))
	 (IF (= "TEXT" IN_3)
	   (PROGN
		 (SETQ C_1 (CDR (ASSOC 1 (CDR IN_2))))
		 (SETQ C_11(ATOf C_1))
		 (setq C_A (STRLEN C_1))
		 (SETQ C_B (ATOI C_1))
		 (SETQ C_BB (ITOA C_B))
		 (SETQ C_BBB (STRLEN C_BB))
		 (SETQ C_CC (- C_BBB C_A))
		 (SETQ C2 (+ USER1 C_11))
		 (setq c_22 (rtos c2 2 C_CC))
	   (SETQ C_3 (SUBST (cons 1 C_22) (cons 1 C_1) IN_2))
		 (ENTMOD C_3)
	   )
	 )
   (SETQ INDEX (+ 1 INDEX))
  )
)

;------------------- Layer change program ----------------------
(vmon)
(defun c:cly()
   (graphscr)
   (prompt "\nSelect entities to be changed ...")
   (setq clen(ssget))
   (setq clo(entget(ssname clen 0)))
   (setq clo(cdr (assoc 8 clo)))
   (prompt "\nType layer name or Pick an entity on desired layer < ")(princ clo)(prompt " >:")
   (setq clstr(getstring))
   (if (/= clstr "")
	   (progn
	(if ( = (tblsearch "layer" clstr) nil)
	(command "layer" "n" clstr "")
	 ))
	   (progn
	  (setq ken(entget (car (entsel))))
		 (setq clstr (cdr (assoc 8 ken))) ;group 8 means layer
   ))
   (command "CHANGE" clen "" "PROP" "LAYER" clstr "")
)

(DEFUN C:DATA()
   (SETQ KANG(ENTGET(CAR(ENTSEL))))
)
(vmon)
(defun c:mmv() ;;; Multi-moving for equal ratio(One-way scale)
   (setq mes(ssget))
   (setq meri(strcase(getstring "\nInput <Scale factor> / Reference :")))
   (if (= meri "R")(kscale) (setq kscalem meri))
   (setq meri(- 1 (atof kscalem)))

   (setq mpt1(getpoint "\nPick base point or line :"))
   (setq mdir(strcase(getstring "\nScale-move direction <X> or <Y> (default = Y) :")))
   (if (= mdir "")(setq mdir "Y"))
   (setq mpt0 mpt1)
   (setq mpt1x (car mpt1) mpt1y (cadr mpt1))
   (if (= mdir "Y")(setq mdir0 "90.0" mpt1 mpt1y)(setq mdir0 "0.0" mpt1 mpt1x))
   (setvar "orthomode" 1)
   (setq mesl(sslength mes) mesi 0)
   (repeat mesl
	  (setq me1(entget(ssname mes mesi)) mpt2(cdr(assoc 10 me1)) )
	  (setq mpt2x(car mpt2) mpt2y(cadr mpt2)  )
	  (if (= mdir "Y")
	  (setq mpt2 mpt2y)
	  (setq mpt2 mpt2x)
	  )
	  (setq mer(rtos(* meri (- mpt1 mpt2))))
	  (setq mfac(strcat "@" mer "<" mdir0))
	  (setq me1(ssname mes mesi))
	  (command "move" me1 "" mpt0 mfac)
	  (setq mesi(+ mesi 1))
   )
)

(defun kscale() ;;;;;;;;; Calulation for scale factor
   (setq kscaler(getreal "\nReference length = "))
   (setq kscalen(getreal "\nNew length = "))
   (setq kscalem(rtos( / kscalen kscaler) 2 8))
)
(DEFUN C:tc()
	(SETQ A (SSGET))
	(SETQ B 0)
	(SETQ C (SSLENGTH A))
	(REPEAT C
	  (SETQ D (SSNAME A B))
	  (SETQ E (ENTGET D))
	  (SETQ F (CDR (ASSOC 0 (CDR E))))
	  (SETQ F1 (ASSOC 1 (CDR E)))
	(IF (= "TEXT" F)
	(PROGN
	  (SETQ G(SSGET))
	  (SETQ H (ASSOC 1 (ENTGET (SSNAME G B))))
	  (SETQ I (SUBST H F1 E))
	  (ENTMOD I)
	))
	   (SETQ B (+ 1 B))
  )
)
(defun C:fdd (/ sset n index txlist tx newtx newlist tx1)
	 (prompt "\nPick TEXTs to change...")
	 (setq sset (ssget))
	 (setq n (sslength sset))
	 (setq newtx (getstring T "\nInput New Text ?: "))
	 (setq index 0)
	 (repeat n
	 (setq txlist (entget (ssname sset index)))
	 (setq index (+ 1 index))
	 (setq tx (assoc 1 txlist))
	 (setq newlist (cons (car tx) newtx))
	 (setq tx1 (subst newlist tx txlist))
	 (entmod tx1)
	 );;REPEAT
	 (princ)
);;DEFUN

(defun c:rc()
  (prompt "/pick select to copy & rotate...")
  (setq SE1 (ssget))
  (setq BA1 (getpoint "/nPick of base point"))
  (setq SE2 (getstring "/nType rotate angle.."))
  (command "copy" se1 "" "0,0" "0,0")
  (command "rotate" se1 "" ba1 se2)
)
;;******************** END OF PROGRAM **********************
